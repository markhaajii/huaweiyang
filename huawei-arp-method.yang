/*
Copyright (C) 2013-2018 Huawei Technologies Co., Ltd. All rights reserved.
*/
submodule huawei-arp-method {
  belongs-to huawei-arp {
    prefix arp;
  }
  import huawei-pub-type {
    prefix pub-type;
  }
  import huawei-extension {
    prefix ext;
  }
  organization
    "Huawei Technologies Co., Ltd.";
  contact
    "Huawei Industrial Base Bantian, Longgang Shenzhen 518129                    
        People's Republic of China                    
        Website: http://www.huawei.com Email: support@huawei.com";
  revision 2018-06-11 {
    description
      "The modifications in the schema file are synchronized to the YANG file.";
    reference
      "Huawei private.";
  }
  revision 2017-12-23 {
    description
      "The modifications in the schema file are synchronized to the YANG file.";
    reference
      "Huawei private.";
  }
  revision 2017-03-23 {
    description
      "Functions supported by the schema are added to the YANG file.";
    reference
      "Huawei private.";
  }
  revision 2013-01-01 {
    description
      "Init revision";
    reference
      "Huawei private.";
  }
  rpc converToStatic {
    description
      "Convert dynamic ARP entries to static ARP entries.";
    ext:node-ref "/arp/arpFailTables/arpFailTable";
    input {
      leaf ifName {
        type pub-type:ifName;
        description
          "Name of an interface where dynamic ARP entries are to be converted to static ARP entries.";
      }
    }
  }
  rpc batchDeleteVpn {
    description
      "Delete static ARP entries by VPN instance.";
    ext:node-ref "/arp/arpStaticTables/arpStaticTable";
    input {
      leaf vrfName {
        type pub-type:vrfName;
        default "_public_";
        description
          "VPN instance name of the static ARP entries to be deleted.";
      }
    }
  }
  rpc batchDeleteAll {
    description
      "Delete all static ARP entries";
    ext:node-ref "/arp/arpStaticTables/arpStaticTable";
  }
}
