/*
Copyright (C) 2013-2018 Huawei Technologies Co., Ltd. All rights reserved.
*/
submodule huawei-bgp-bgpcomm {
  belongs-to huawei-bgp {
    prefix bgp;
  }
  import huawei-acl {
    prefix acl;
  }
  import huawei-ifm {
    prefix ifm;
  }
  import huawei-mpls {
    prefix mpls;
  }
  import huawei-bfd {
    prefix bfd;
  }
  import huawei-l3vpn {
    prefix l3vpn;
  }
  import huawei-pub-type {
    prefix pub-type;
  }
  import huawei-rtp {
    prefix rtp;
  }
  import huawei-tnlm {
    prefix tnlm;
  }
  import ietf-inet-types {
    prefix inet;
  }
  import ietf-yang-types {
    prefix yang;
  }
  import huawei-extension {
    prefix ext;
  }
  import huawei-segripv6 {
    prefix segripv6;
  }
  include huawei-bgp-rpd;
  include huawei-bgp-type;
  
  organization
    "Huawei Technologies Co., Ltd.";
  contact
    "Huawei Industrial Base Bantian, Longgang Shenzhen 518129                    
        People's Republic of China                    
        Website: http://www.huawei.com Email: support@huawei.com";
  description
    "Description of submodule bgp_bgpcomm";
  revision 2018-06-11 {
    description
      "The modifications in the schema file are synchronized to the YANG file.";
    reference
      "Huawei private.";
  }
  revision 2017-12-23 {
    description
      "The modifications in the schema file are synchronized to the YANG file.";
    reference
      "Huawei private.";
  }
  revision 2017-03-23 {
    description
      "Functions supported by the schema are added to the YANG file.";
    reference
      "Huawei private.";
  }
  revision 2013-01-01 {
    description
      "Init revision";
    reference
      "Huawei private.";
  }
  grouping bgp_bgpcomm_bgpcomm_type {
    description
      "";
    container bgpSite {
      description
        "Site containing the global BGP information, such as the protocol version, AS number, and system identifier.";
      leaf bgpVersion {
        type uint8;
        config false;
        description
          "BGP version, which is BGP-4 at present. BGP-4 provides a new mechanism to support Classless Inter-Domain Routing (CIDR). In this case, the network prefix-based advertisement is supported and the concept of class for a BGP network is canceled in the network prefix-supported advertisements. Another mechanism is also introduced to support route summarization, including the summarization of AS paths.";
      }
      leaf bgpEnable {
        type boolean;
        must "(../bgpEnable='true' and ../asNumber) or (../bgpEnable='false' and not(../asNumber))";
        default "false";
        description
          "Enable BGP. By default, BGP is disabled.";
      }
      leaf asNumber {
        type asNumberValidate;
        must "(../bgpEnable='true' and ../asNumber) or (../bgpEnable='false' and not(../asNumber))";
        description
          "Local AS number, which can be in either of the two formats:
The two-byte format is X. X is an integer ranging from 1 to 65535.
The four-byte format is X.Y and X. When the format is X.Y, X and Y are both integers, with the value of X ranging from 1 to 65535, and the value of Y ranging from 0 to 65535; when the format is X, X is an interger, with the value ranging from 1 to 4294967295.
An AS consists of multiple routers managed based on the same techniques. Interior Gateway Protocol (IGP) and universal routing metric packets are used inside an AS, and Exterior Gateway Protocol (EGP) is used outside to send packets to other ASs. With the development of this definition, one AS usually uses multiple IGPs and metrics. Even though multiple IGPs and metrics are used, the routing plan and destination reachability of an AS are consistent with those of another AS. The local AS number cannot be configured same as the confederation sub-ASs.";
        ext:allowDelete "true";
      }
      leaf gracefulRestart {
        when "not(../bgpEnable='false')";
        type boolean;
        default "false";
        description
          "Enable GR of the BGP speaker in the specified address family, peer address, or peer group. When GR is enabled, the BGP speaker enabled with GR keeps the forwarding state and sends the End-Of-RIB flag during the restart. In this case, however, the BGP speaker may not maintain the forwarding table. Enabling or disabling GR may delete and re-establish all sessions and instances.";
      }
      leaf timeWaitForRib {
        when "../gracefulRestart='true'";
        type uint32 {
          range "3..3000";
        }
        default "600";
        description
          "Period of waiting for the End-Of-RIB flag. The value is an integer in seconds. The default value is 600. When a BGP session is established or re-established, the router enabled with GR should receive the End-Of-RIB flag in this period. If the router does not receive the End-Of-RIB flag in this period, ensure that the router can exit from the GR process.";
        ext:allowDelete "true";
      }
      leaf asPathLimit {
        when "not(../bgpEnable='false')";
        type uint16 {
          range "1..2000";
        }
        description
          "Maximum number of AS numbers in the AS_Path attribute. The default value is 255.";
        ext:allowDelete "true";
      }
      leaf checkFirstAs {
        when "not(../bgpEnable='false')";
        type boolean;
        default "true";
        description
          "Check the first AS in the AS_Path of the update messages from EBGP peers. By default, this function is enabled.";
      }
      leaf confedIdNumber {
        when "not(../bgpEnable='false')";
        type asNumberValidate;
        description
          "Confederation ID.";
        ext:allowDelete "true";
      }
      leaf confedNonstanded {
        when "not(../bgpEnable='false')";
        type boolean;
        default "false";
        description
          "Configure the device to be compatible with devices in a nonstandard confederation.";
      }
      leaf bgpRidAutoSel {
        when "not(../bgpEnable='false')";
        type boolean;
        default "false";
        description
          "By default, a BGP VPN instance does not automatically select a router ID. If a BGP VPN instance is not enabled to select a router ID, a router ID can be configured for the BGP VPN instance. If no router ID is configured for the BGP VPN instance, the BGP VPN instance inherits the router ID of the public network instance. If a BGP VPN instance is enabled to select a router ID, it uses the address of an interface bound to a VPN as the router ID based on the following rules: 
1. If Loopback interfaces configured with IP addresses exist, the largest IP address among the IP addresses of the Loopback interfaces is selected as the router ID. 
2. If there is no Loopback interface configured with an IP address, the largest IP address among the IP addresses of other interfaces is selected as the router ID, regardless of whether the interface is Up.";
      }
      leaf keepAllRoutes {
        when "not(../bgpEnable='false')";
        type boolean;
        default "false";
        description
          "Save all the updated information about BGP routes from a peer or peer group after a BGP connection is established, even though these BGP routes fail to match the routing policy on the ingress. By default, only the updated information about BGP routes from a specified peer is saved on condition that the routes match the routing policy on the ingress. If a router supports route refreshing, this option is not required.";
      }
      leaf memoryLimit {
        when "not(../bgpEnable='false')";
        type boolean;
        default "false";
        description
          "Support BGP RIB memory protection. By default, the function is not enabled. With BGP RIB memory protection, routes are no longer received after the RIB memory is overloaded.";
      }
      leaf grPeerReset {
        when "../gracefulRestart='true'";
        type boolean;
        default "false";
        description
          "Peer disconnection through GR.";
      }
      leaf isShutdown {
        when "not(../bgpEnable='false')";
        type boolean;
        default "false";
        description
          "Interrupt BGP all neighbor.";
      }
      leaf pathAttrErrCap {
        when "not(../bgpEnable='false')";
        type boolean;
        default "false";
        description
          "Discard the error route attribute";
      }
      leaf suppressInterval {
        when "../bgpEnable='true'";
        type uint32 {
          range "1..65535";
        }
        must "(../holdInterval>../suppressInterval) and (../clearInterval>../suppressInterval)";
        default "60";
        description
          "Specifies the reference period used to add penalty in case of next hop flapping in seconds. By default, the value is 60 seconds.";
        ext:allowDelete "true";
      }
      leaf holdInterval {
        when "../bgpEnable='true'";
        type uint32 {
          range "1..65535";
        }
        must "(../holdInterval>../suppressInterval) and (../clearInterval>../holdInterval)";
        default "120";
        description
          "Specifies the reference period used to hold penalty in case of next hop flapping in seconds. By default, the value is 120 seconds.";
        ext:allowDelete "true";
      }
      leaf clearInterval {
        when "../bgpEnable='true'";
        type uint32 {
          range "1..65535";
        }
        must "(../clearInterval>../suppressInterval) and (../clearInterval>../holdInterval)";
        default "600";
        description
          "Specifies the reference period used to clear penalty in case of next hop flapping in seconds. By default, the value is 600 seconds.";
        ext:allowDelete "true";
      }
      leaf restartTime {
        when "../gracefulRestart='true'";
        type uint16 {
          range "3..3600";
        }
        default "150";
        description
          "Specifies the maximum time during which a peer waits for a BGP session reestablishment. It is an integer ranging from 3 to 3600, in seconds. By default, the value is 150 seconds.";
        ext:allowDelete "true";
      }
      leaf lowestPriority {
        when "not(../bgpEnable='false')";
        type boolean;
        default "false";
        description
          "Reduce route priority to lowest.";
        ext:allowDelete "true";
      }
      leaf delayTime {
        when "../lowestPriority='true'";
        type uint32 {
          range "1..864000";
        }
        description
          "Specifies the delayTime.";
        ext:allowDelete "true";
      }
      leaf localIfnetMtu {
        when "not(../bgpEnable='false')";
        type uint16 {
          range "46..65535";
        }
        default "1500";
        description
          "BGP LOCALIFNET MTU";
        ext:allowDelete "true";
      }
      leaf private4byteAs {
        when "not(../bgpEnable='false')";
        type boolean;
        default "false";
        description
          "Support BGP private 4 byte AS. By default, the BGP private as is from 64512 to 65535. With BGP private-4-byte-as, BGP private as is from 64512 to 65535 and from 4200000000 to 4294967294.";
      }
      leaf localCrossNoMed {
        when "not(../bgpEnable='false')";
        type boolean;
        default "false";
        description
          "Local cross routing non-med.";
      }
    }
    container bgpConfedPeerAss {
      when "not(../bgpSite/bgpEnable='false')";
      description
        "Confederation AS list.";
      list bgpConfedPeerAs {
        key "confedPeerAsNum";
        max-elements  "32";
        description
          "Confederation AS.";
        leaf confedPeerAsNum {
          type asNumberValidate;
          description
            "Confederation AS number, which can be in either of the two formats:
The two-byte format is X. X is an integer ranging from 1 to 65535.
The four-byte format is X.Y and X. When the format is X.Y, X and Y are both integers, with the value of X ranging from 1 to 65535, and the value of Y ranging from 0 to 65535; when the format is X, X is an interger, with the value of X ranging from 1 to 4294967295. The confederation sub-ASs cannot be configured same as the local AS number.";
        }
      }
    }
    container bgpVrfs {
      when "not(../bgpSite/bgpEnable='false')";
      description
        "Configure the list of all BGP instances.";
      list bgpVrf {
        key "vrfName";
        max-elements  "4096";
        description
          "Create a BGP instance.";
        leaf vrfName {
          type leafref {
            path "/l3vpn:l3vpn/l3vpn:l3vpncomm/l3vpn:l3vpnInstances/l3vpn:l3vpnInstance/l3vpn:vrfName";
          }
          description
            "VPN name of a BGP instance. The name is a case-sensitive string of characters. The BGP instance can be used only after the corresponding VPN instance is created. ";
        }
        leaf vrfSession {
          when "not(../vrfName='_public_')";
          type boolean;
          default "true";
          description
            "Create Vpn session View.";
        }
        leaf vrfRidAutoSel {
          when "../vrfName!='_public_'";
          type boolean;
          default "false";
          description
            "By default, a BGP VPN instance does not automatically select a router ID. If a BGP VPN instance is not enabled to select a router ID, a router ID can be configured for the BGP VPN instance. If no router ID is configured for the BGP VPN instance, the BGP VPN instance inherits the router ID of the public network instance. If a BGP VPN instance is enabled to select a router ID, it uses the address of an interface bound to a VPN as the router ID based on the following rules: 
1. If Loopback interfaces configured with IP addresses exist, the largest IP address among the IP addresses of the Loopback interfaces is selected as the router ID. 
2. If there is no Loopback interface configured with an IP address, the largest IP address among the IP addresses of other interfaces is selected as the router ID, regardless of whether the interface is Up.";
        }
        leaf routerId {
          type inet:ipv4-address-no-zone;
          description
            "ID of a router that is in IPv4 address format. Certain dynamic routing protocols require a router ID. If no router ID is specified for a router when these protocols are enabled, the router ID in the RM module is used by default. The default router ID in the RM module is 0.0.0.0 when the router is not configured with any interface. 
The rules for selecting a router ID are as follows:
1. If you set a router ID through this configuration, the set router ID is used. If the router ID is not set, you need to select a router ID according to the following rules:
(1) If loopback interfaces configured with IP addresses exist, the largest IP address among the IP addresses of the loopback interfaces is selected as the router ID.
(2) If no loopback interface configured with an IP address exists, the largest IP address among the IP addresses of other interfaces is selected as the router ID, regardless of whether the interface is Up.
The router ID is reselected only when the interface address that is selected as the router ID is deleted or changed. The router ID is not reselected in any of the following cases:
a. The interface is Down.
b. A loopback interface is configured when the IP address of a non-loopback interface is selected as the router ID.
c. A larger IP address of an interface is configured.
2. Each VPN instance selects the router ID from the addresses of the interfaces of the VPN instance according to the preceding rules.
3. When both the AMB and SMB exist on the router, the system backs up the router ID set through the related command and the router ID that is selected from IP addresses of the interfaces. After the active/standby switchover is performed, the system checks the validity of the router ID selected from the interface addresses. If the router ID is invalid, the system reselects a router ID.";
          ext:allowDelete "true";
        }
        leaf effectRouterId {
          type inet:ipv4-address-no-zone;
          default "0.0.0.0";
          config false;
          description
            "Router ID that takes effect.";
        }
        leaf keepaliveTime {
          when "../vrfName='_public_'";
          type uint32 {
            range "0..21845";
          }
          default "60";
          description
            "If the value of a timer changes, the BGP peer relationship between the routers is disconnected. This is because the peers need to re-negotiate the Keepalive time and hold time. Therefore, confirm the action before you change the value of the timer. The Keepalive time should be at least three times of the hold time.";
          ext:allowDelete "true";
        }
        leaf holdTime {
          when "../vrfName='_public_'";
          type uint32 {
            range "0..65535";
          }
          must "(../holdTime!=1) and (../holdTime!=2) and (../holdTime>=../keepaliveTime*3) and (../holdTime>=../minHoldTime)";
          default "180";
          description
            "Hold time, in seconds. The value of the hold time can be 0 or range from 3 to 65535. When setting keepalive-time and hold-time, note the following:
1. The values of keepalive-time and hold-time cannot both be 0. Otherwise, the BGP timer becomes invalid. That is, BGP does not detect link faults according to the timer.
2. The value of hold-time is much greater than that of keepalive-time, such as, keepalive 1 and hold 65535. If the value of hold-time is too large, BGP cannot detect link faults timely.
The priority of a timer is lower than that of a peer timer.
After a connection is established between peers, the values of keepalive-time and hold-time are negotiated by the peers. The smaller value of hold-time contained in Open packets of both peers is taken as the value of hold-time. The smaller value of the locally set value of keepalive-time and one third of the value of hold-time is taken as the value of keepalive-time.";
          ext:allowDelete "true";
        }
        leaf minHoldTime {
          when "../vrfName='_public_'";
          type uint32 {
            range "0..65535";
          }
          default "0";
          description
            "The minimum hold time is either 0 or an integer ranging from 20 to 65535, in seconds. If the value is changed, the new value takes effect since the next peer relationship establishment. During the peer relationship establishment, the local device checks the hold time of the remote end. If the hold time is less than the minimum hold time, the local device sends an error packet with error code 02 and subcode 06, and the peer relationship fails to be established.";
          ext:allowDelete "true";
        }
        leaf connRetryTime {
          when "../vrfName='_public_'";
          type uint16 {
            range "1..65535";
          }
          default "32";
          description
            "ConnectRetry interval. The value is an integer, in seconds. The default value is 32s.";
          ext:allowDelete "true";
        }
        leaf defaultAfType {
          when "../vrfName!='_public_'";
          type bgpcommVrfPrefixType;
          must "not(../vrfName!='_public_') or (../vrfName!='_public_')";
          default "ipv4uni";
          description
            "Type of a created address family, which can be IPv4 unicast or IPv6 unicast. The default type is IPv4 unicast. This option takes effect only when a BGP instance is created for the first time. ";
          ext:allowDelete "true";
        }
        container bgpPeerGroups {
          description
            "List of BGP peer groups. The BGP peer groups can help you simplify the configurations. If you want to perform the same configuration for several peers, you can create a peer group and then configure the peer group. After you add these peers to the peer group, all these peers will have the same configurations as the peer group. ";
          list bgpPeerGroup {
            key "afType groupName";
            description
              "Information about a BGP peer group.";
            leaf afType {
              type bgpcommGroupAddrFamily;
              must "not(../../../vrfName='_public_') or (../../../vrfName='_public_' and (../afType='public') )";
              description
                "Address family type of a peer group. For a public instance, this value cannot be modified. Since a VPN instance is related to its address family, you need to specify the address family type when creating a peer group in the VPN instance. For example, if you want to create an address family in a VPN instance of IPv4 unicast, choose IPv4 unicast as the address family type.";
            }
            leaf groupName {
              type string {
                length "1..47";
                pattern '([^\? ]+)';
              }
              description
                "Specify the name of a peer group. The value is a string of characters, spaces not supported.";
            }
            leaf groupType {
              type bgpcommPeerType;
              mandatory true;
              description
                "Specify the type of a peer group. The value can be IBGP or EBGP. The default value is IBGP.";
            }
            leaf groupAs {
              when "not(../groupType='ibgp')";
              type asNumberValidate;
              description
                "Specify the AS number of a peer group. The AS number is in either a 2-byte or 4-byte format. 
The two-byte format is X. X is an integer ranging from 1 to 65535.
The four-byte format is X.Y and X. When the format is X.Y, X and Y are both integers, with the value of X ranging from 1 to 65535, and the value of Y ranging from 0 to 65535; when the format is X, X is an interger, with the value of X ranging from 1 to 4294967295.";
              ext:allowDelete "true";
            }
            leaf description {
              type string {
                length "1..255";
                pattern '([^?]*)';
              }
              description
                "Specify the description of a peer group. The value is a string, which can be letters or digits, spaces supported. By default, no description is configured.";
              ext:allowDelete "true";
            }
            leaf fakeAs {
              when "not(../groupType='ibgp')";
              type asNumberValidate;
              description
                "Fake AS number that is specified for a local peer. By default, a peer uses the actual AS number of the local end.
An AS number can be in either two-byte format or four-byte format:
The two-byte format is X. X is an integer ranging from 1 to 65535.
The four-byte format is X.Y and X. When the format is X.Y, X and Y are both integers, with the value of X ranging from 1 to 65535, and the value of Y ranging from 0 to 65535; when the format is X, X is an interger, with the value of X ranging from 1 to 4294967295.";
              ext:allowDelete "true";
            }
            leaf dualAs {
              when "../fakeAs";
              type boolean;
              default "false";
              description
                "By default, dual AS is not enabled, and the remote EBGP peer uses the fake AS number when specifying the AS number for a local peer. 
After dual AS is enabled, the remote EBGP peer can use the actual or fake AS number when specifying the AS number for a local peer. The local peer uses the fake and actual AS numbers to establish a BGP peer relationship with the remote end and identifies the AS number configured by the remote end through the error code (OPEN Message Error) and sub-error code (Bad Peer AS) of the Notification message from the remote end.";
            }
            leaf conventional {
              when "not(../../../vrfName!='_public_' and ../afType='ipv6uni')";
              type boolean;
              default "false";
              description
                "Enable general router functions on peers. In conventional mode, not all the extended router functions, such as, route refreshing, GR, and multi-address family negotiation, are available. Therefore, the router of a new version can be compatible with the routers of earlier versions.";
            }
            leaf routeRefresh {
              type boolean;
              default "true";
              description
                "Enable BGP to advertise Refresh messages to peers. By default, this function is enabled.";
            }
            leaf fourByteAs {
              type boolean;
              default "true";
              description
                "Enables BGP to advertise routes carrying 4-byte AS numbers to peers. By default, the function is enabled. After the 4-byte AS number function is disabled, Open packets will not carry 4-byte AS number capability flag, and peer ends will not know that local ends have the 4-byte AS number function. The 4-byte AS number function cannot be disabled from peers (peer groups) if a 4-byte AS number, fake AS number, or confederation ID is configured on a router and the AS number of a peer is 4-byte.  If the 4-byte AS number function is disabled in such a situation, BGP sessions may fail to be established, and route transmission may be affected.";
            }
            leaf isIgnore {
              type boolean;
              default "false";
              description
                "Tear down sessions between peers and clear all related routing information. By default, this function is disabled.";
            }
            leaf localIfName {
              type leafref {
                path "/ifm:ifm/ifm:interfaces/ifm:interface/ifm:ifName";
              }
              description
                "Name of a source interface that sends BGP packets. By default, the outbound interface of a BGP packet serves as the source interface of a BGP packet. To ensure that a router can send BGP packets when a physical interface fails, you can configure the source interface that sends BGP packets as a loopback interface. When using the loopback interface as the source interface, note the following points:
1. The address of the loopback interface of the BGP peer must be reachable.
2. For an EBGP connection, configure the maximum number of hops and allow EBGP peer relationships to be established in indirect mode.";
              ext:allowDelete "true";
            }
            leaf localIfAddress {
              type inet:ip-address-no-zone;
              description
                "Name of a source interface that sends BGP packets. By default, the outbound interface of a BGP packet serves as the source interface of a BGP packet. To ensure that a router can send BGP packets when a physical interface fails, you can configure the source interface that sends BGP packets as a loopback interface. When using the loopback interface as the source interface, note the following points:
1. The address of the loopback interface of the BGP peer must be reachable.
2. For an EBGP connection, configure the maximum number of hops and allow EBGP peer relationships to be established in indirect mode.";
              ext:allowDelete "true";
            }
            leaf ebgpMaxHop {
              when "not(../groupType='ibgp')";
              type uint32 {
                range "1..255";
              }
              must "not(../validTtlHops) and ../groupType='ebgp'";
              default "1";
              description
                "Maximum number of hops in an indirect EBGP connection. By default, EBGP connections can be established only between directly connected peers. The function must be configured on both ends.";
              ext:allowDelete "true";
            }
            leaf validTtlHops {
              type uint16 {
                range "1..255";
              }
              must "not(../ebgpMaxHop and ../ebgpMaxHop>1 and ../ebgpMaxHop<=255)";
              description
                "Enable GTSM on a peer or peer group. The valid-TTL-Value parameter is used to specify the number of TTL hops to be detected. If the value is configured as hops, the valid TTL range of the detected packet is [255-hops+1, 255]. 
";
              ext:allowDelete "true";
            }
            leaf connectMode {
              type bgpcommPeerConnectMode;
              default "null";
              description
                "The value can be Connect-only, Listen-only, or Both. If the value is Connect-only, the specified peer or peer group only initiatively sends connection requests, instead of listening to connection requests. If the value is Listen-only, the specified peer or peer group only listens to connection requests, instead of initiatively sending connection requests. If the value is Both, the specified peer or peer group not only initiatively sends connection requests, but also listens to connection requests. The default value is Both.";
              ext:allowDelete "true";
            }
            leaf isLogChange {
              type boolean;
              default "true";
              description
                "Enable BGP to record the session status and events of the specified peer or peer group. By default, the function is enabled.";
            }
            leaf pswdType {
              type bgpcommPasswordType;
              must "not(../pswdType and ../pswdType!='null' and ../keyChainName)";
              default "null";
              description
                "Enable BGP peers to establish a TCP connection and perform the Message Digest 5 (MD5) authentication for BGP messages. Plaintexts and ciphertexts are supported.";
              ext:allowDelete "true";
            }
            leaf pswdCipherText {
              when "not(not(../pswdType))";
              type pub-type:passwordExtend;
              description
                "Enable BGP peers to establish a TCP connection and perform the Message Digest 5 (MD5) authentication for BGP messages. The character string in a password identifies the contents of the password, spaces not supported. The TCP connection can be established only when the same MD5 authentication password is set on both ends. If a plaintext is used, the maximum password length is 255. If a ciphertext is used, the maximum password length is 432. If the length is set to 0, no password is set.";
              ext:allowDelete "true";
            }
            leaf keepAliveTime {
              type uint32 {
                range "0..21845";
              }
              default "60";
              description
                "Specify the Keepalive time of a peer or peer group. The value is an integer, in seconds. If the value of a timer changes, the peers need to re-negotiate the interval value for the keepalive-time and hold-time. This disconnects the BGP peer relationship between the routers. Therefore, you need to double check whether it is a must to change the value of the timer. Ensure that the hold time is at least three times longer than the keepalive time when you configure the BGP timer.";
              ext:allowDelete "true";
            }
            leaf holdTime {
              type uint32 {
                range "0..65535";
              }
              must "(../holdTime!=1) and (../holdTime!=2) and (../holdTime>=../keepAliveTime*3) and (../holdTime>=../minHoldTime)";
              default "180";
              description
                "Specify the Hold time of a peer or peer group. The value is either 0 or an integer ranging from 0 to 65535, in seconds. When setting the timer values of keepalive-time and hold-time, avoid the following settings: 1.The interval values of keepalive-time and hold-time are both set to 0. This will cause BGP timer to become invalid, and BGP will not detect link faults based on the timer. 
2. The interval value of hold-time is much greater than that of keepalive-time. For example, the interval value of keepalive-time is 1, and that of hold-time is 65535. If the interval value of hold-time is too large, BGP will not be able to detect link faults in time. The priority of the timer configured here is lower than that of timer configured with interval values of keepalive-time and hold-time of a peer. After a connection is established between peers, the interval values of keepalive-time and hold-time are negotiated by the peers. The smaller interval value of hold-time contained in Open packets of both peers is taken as the interval value of hold-time. The smaller interval value of one third of the interval value of hold-time and the locally set interval value of keepalive-time is taken as the interval value of keepalive-time.";
              ext:allowDelete "true";
            }
            leaf minHoldTime {
              type uint32 {
                range "0..65535";
              }
              default "0";
              description
                "The minimum hold time is either 0 or an integer ranging from 20 to 65535, in seconds. If the value is changed, the new value takes effect since the next peer relationship establishment. During the peer relationship establishment, the local device checks the hold time of the remote end. If the hold time is less than the minimum hold time, the local device sends an error packet with error code 02 and subcode 06, and the peer relationship fails to be established.";
              ext:allowDelete "true";
            }
            leaf keyChainName {
              type string {
                length "1..47";
              }
              must "not(../pswdType and ../pswdType!='null' and ../keyChainName)";
              description
                "Specify the Keychain authentication name used when BGP peers establish a TCP connection. The value is a string, spaces not supported. By default, the Keychain authentication is not configured. Keychain authentication mode and password authentication mode are mutually exclusive. Configuring Keychain authentication can enhance the security of the TCP connections between BGP peers. Keychain authentication using the same encryption algorithm and password must be configured on the two ends of BGP peers to establish a TCP connection and exchange BGP packets. Before configuring BGP Keychain authentication, you need to configure Keychain according to keychain name. Otherwise, the TCP connections between the BGP peers cannot be established.";
              ext:allowDelete "true";
            }
            leaf pathMTUD {
              type boolean;
              default "false";
              description
                "path-mtu auto-discovery.";
            }
            leaf trackingEnable {
              type boolean;
              default "false";
              description
                "Enable peer tracking, After peer tracking is enabled, the device can fast detect the unreachability of a peer and reset the session.";
              ext:allowDelete "true";
            }
            leaf trackDelayTime {
              when "../trackingEnable='true'";
              type uint16 {
                range "0..65535";
              }
              default "0";
              description
                "Specify the delay to reset the session, in seconds.";
              ext:allowDelete "true";
            }
            leaf connRetryTime {
              type uint16 {
                range "1..65535";
              }
              default "32";
              description
                "ConnectRetry interval. The value is an integer, in seconds. The default value is 32s.";
              ext:allowDelete "true";
            }
            leaf tcpMSS {
              type uint16 {
                range "176..4096";
              }
              description
                "Maximum TCP MSS value used for TCP connection establishment for a peer group. ";
              ext:allowDelete "true";
            }
            leaf mplsLocalIfnetDisable {
              when "../../../vrfName='_public_' and ../groupType='ebgp'";
              type boolean;
              default "false";
              description
                "Disable MPLS local IFNET tunnel creation. By default, MPLS local IFNET tunnels can be created.";
              ext:allowDelete "true";
            }
            leaf prependGlobalAs {
              when "not(../groupType='ibgp' or not(../fakeAs))";
              type boolean;
              default "false";
              description
                "Add the global AS number to the Update packets to be advertised.";
            }
            leaf prependFakeAs {
              when "not(../groupType='ibgp' or not(../fakeAs))";
              type boolean;
              default "false";
              description
                "Add the Fake AS number to received Update packets.";
            }
            leaf pathAttrDiscardIdMap {
              type pub-type:id-range {
                ext:value-range '1..255';
                pattern '((2[0-5][0-5]|1[0-9][0-9]|[1-9][0-9]|[1-9])?(-(2[0-5][0-5]|1[0-9][0-9]|[1-9][0-9]|[1-9]))?(,((2[0-5][0-5]|1[0-9][0-9]|[1-9][0-9]|[1-9])(-(2[0-5][0-5]|1[0-9][0-9]|[1-9][0-9]|[1-9]))?))*)|((([\+|\-](2[0-5][0-5]|1[0-9][0-9]|[1-9][0-9]|[1-9]))|([\+|\-]\((2[0-5][0-5]|1[0-9][0-9]|[1-9][0-9]|[1-9])-(2[0-5][0-5]|1[0-9][0-9]|[1-9][0-9]|[1-9])\)))?(,(([\+|\-](2[0-5][0-5]|1[0-9][0-9]|[1-9][0-9]|[1-9]))|([\+|\-]\((2[0-5][0-5]|1[0-9][0-9]|[1-9][0-9]|[1-9])-(2[0-5][0-5]|1[0-9][0-9]|[1-9][0-9]|[1-9])\))))*)';
              }
              description
                "Specify a discard attrId list.The format of a list is as follows:20-30,55.No support the attribute ids as follows:
IBGP peer or CONFEDERATION EBGP peer or CONFEDERATION IBGP peer: 1(ORIGIN),2(AS_PATH),3(NEXT_HOP),4(MED),5(LOCALPREF),8(COMMUNITY),9(ORIGINATOR),10(CLUSTER-ID),14(MP_NLRI),15(MP_UNLRI),16(EXTCOMMUNITY),
EBGP peer: 1(ORIGIN),2(AS_PATH),3(NEXT_HOP),4(MED),8(COMMUNITY),14(MP_NLRI),15(MP_UNLRI),16(EXTCOMMUNITY)";
              ext:allowDelete "true";
            }
            leaf pathAttrWithdrawIdMap {
              type pub-type:id-range {
                ext:value-range '1..255';
                pattern '((2[0-5][0-5]|1[0-9][0-9]|[1-9][0-9]|[1-9])?(-(2[0-5][0-5]|1[0-9][0-9]|[1-9][0-9]|[1-9]))?(,((2[0-5][0-5]|1[0-9][0-9]|[1-9][0-9]|[1-9])(-(2[0-5][0-5]|1[0-9][0-9]|[1-9][0-9]|[1-9]))?))*)|((([\+|\-](2[0-5][0-5]|1[0-9][0-9]|[1-9][0-9]|[1-9]))|([\+|\-]\((2[0-5][0-5]|1[0-9][0-9]|[1-9][0-9]|[1-9])-(2[0-5][0-5]|1[0-9][0-9]|[1-9][0-9]|[1-9])\)))?(,(([\+|\-](2[0-5][0-5]|1[0-9][0-9]|[1-9][0-9]|[1-9]))|([\+|\-]\((2[0-5][0-5]|1[0-9][0-9]|[1-9][0-9]|[1-9])-(2[0-5][0-5]|1[0-9][0-9]|[1-9][0-9]|[1-9])\))))*)';
              }
              description
                "Specify a withdraw attrId list.The format of a list is as follows:20-30,55.No support the attribute ids as follows:
IBGP peer or CONFEDERATION EBGP peer or CONFEDERATION IBGP peer: 1(ORIGIN),2(AS_PATH),3(NEXT_HOP),4(MED),5(LOCALPREF),8(COMMUNITY),9(ORIGINATOR),10(CLUSTER-ID),14(MP_NLRI),15(MP_UNLRI),16(EXTCOMMUNITY),
EBGP peer: 1(ORIGIN),2(AS_PATH),3(NEXT_HOP),4(MED),8(COMMUNITY),14(MP_NLRI),15(MP_UNLRI),16(EXTCOMMUNITY)";
              ext:allowDelete "true";
            }
            leaf checkFirstAs {
              type bgpCheckFirstAsTriState;
              default "default";
              description
                "Check the first AS in the AS_Path of the update messages from EBGP peers. By default, this function is enabled.";
            }
            container peerMembers {
              config false;
              description
                "List of members in a peer group.";
              list peerMember {
                key "peerSession";
                config false;
                description
                  "Member in a peer group.";
                leaf peerSession {
                  type string {
                    length "1..512";
                  }
                  config false;
                  description
                    "Specify the address of the peer joining the peer group.";
                }
              }
            }
            container peerGroupBfd {
              description
                "Configure BFD.";
              leaf multiplier {
                type uint32 {
                  range "3..50";
                }
                default "3";
                description
                  "Specify the detection multiplier. The default value is 3.";
                ext:allowDelete "true";
              }
              leaf isBfdEnable {
                type boolean;
                default "false";
                description
                  "Configure BFD.";
              }
              leaf rxInterval {
                type uint32 {
                  range "3..1000";
                }
                description
                  "Specify the minimum interval at which BFD packets are received. By default, the value is determined by the PAF file.";
                ext:allowDelete "true";
              }
              leaf txInterval {
                type uint32 {
                  range "3..1000";
                }
                description
                  "Specify the minimum interval at which BFD packets are sent. By default, the value is determined by the PAF file.";
                ext:allowDelete "true";
              }
              leaf isSingleHop {
                when "../isBfdEnable='true'";
                type boolean;
                default "false";
                description
                  "The single hop mode is preferred during the BFD session establishment between IBGP peers.";
              }
              leaf bfdCompatible {
                when "../isBfdEnable='true'";
                type boolean;
                default "false";
                description
                  "Compatible.";
              }
              leaf perLinkEcho {
                when "../isBfdEnable='true'";
                type boolean;
                must "../isSingleHop='false' and ../bfdCompatible='false' and ../isBfdEnable='true' or (not(../isSingleHop='false' and ../bfdCompatible='false' and ../isBfdEnable='true') and ../perLinkEcho='false')";
                default "false";
                description
                  "The per-link one-arm-echo mode is preferred during the BFD session establishment between IBGP peers.";
              }
            }
          }
        }
        container bgpPeers {
          description
            "List of BGP peers.";
          list bgpPeer {
            key "peerAddr";
            description
              "Configurations of a single BGP peer.";
            leaf peerAddr {
              type inet:ip-address-no-zone;
              description
                "Connection address of a peer, which can be an IPv4 or IPv6 address.";
            }
            leaf groupName {
              type leafref {
                path "../../../bgpPeerGroups/bgpPeerGroup/groupName";
              }
              description
                "Specify the name of a peer group that BGP peers need to join. That must be selected group name or AS when creating, and the value is a string, spaces not supported. By default, BGP peers join no peer group. BGP peers distinguish the peer group type when joining a peer group. IBGP peers cannot join an EBGP peer group.  BGP peers will be deleted when they leave a peer group. ";
              ext:allowDelete "true";
            }
            leaf remoteAs {
              type asNumberValidate;
              description
                "AS number of a peer, which must be selected or group name when creating, and which can be in either two-byte format or four-byte format:
The two-byte format is X. X is an integer ranging from 1 to 65535.
The four-byte format is X.Y and X. When the format is X.Y, X and Y are both integers, with the value of X ranging from 1 to 65535, and the value of Y ranging from 0 to 65535; when the format is X, X is an interger, with the value of X ranging from 1 to 4294967295.";
              ext:allowDelete "true";
            }
            leaf description {
              type string {
                length "1..255";
                pattern '([^?]*)';
              }
              description
                "Description of a peer, which can be letters or digits. The description is a string of 1 to 80 characters, with spaces supported. By default, no description is configured for a peer.";
              ext:allowDelete "true";
            }
            leaf fakeAs {
              type asNumberValidate;
              description
                "Fake AS number that is specified for a local peer. By default, a peer uses the actual AS number of the local end.
An AS number can be in either two-byte format or four-byte format:
The two-byte format is X. X is an integer ranging from 1 to 65535.
The four-byte format is X.Y and X. When the format is X.Y, X and Y are both integers, with the value of X ranging from 1 to 65535, and the value of Y ranging from 0 to 65535; when the format is X, X is an interger, with the value of X ranging from 1 to 4294967295.";
              ext:allowDelete "true";
            }
            leaf dualAs {
              when "../fakeAs";
              type boolean;
              default "false";
              description
                "By default, dual AS is not enabled, and the remote EBGP peer uses the fake AS number when specifying the AS number for a local peer. 
After dual AS is enabled, the remote EBGP peer can use the actual or fake AS number when specifying the AS number for a local peer. The local peer uses the fake and actual AS numbers to establish a BGP peer relationship with the remote end and identifies the AS number configured by the remote end through the error code (OPEN Message Error) and sub-error code (Bad Peer AS) of the Notification message from the remote end.";
            }
            leaf conventional {
              type boolean;
              default "false";
              description
                "Enable general router functions on peers. In conventional mode, not all the extended router functions, such as, route refreshing, GR, and multi-address family negotiation, are available. Therefore, the router of a new version can be compatible with the routers of earlier versions.";
            }
            leaf routeRefresh {
              type boolean;
              default "true";
              description
                "Enable BGP to advertise Refresh messages to peers. By default, this function is enabled.";
            }
            leaf fourByteAs {
              type boolean;
              default "true";
              description
                "Enables BGP to advertise routes carrying 4-byte AS numbers to peers. By default, the function is enabled. After the 4-byte AS number function is disabled, Open packets will not carry 4-byte AS number capability flag, and peer ends will not know that local ends have the 4-byte AS number function. The 4-byte AS number function cannot be disabled from peers (peer groups) if a 4-byte AS number, fake AS number, or confederation ID is configured on a router and the AS number of a peer is 4-byte.  If the 4-byte AS number function is disabled in such a situation, BGP sessions may fail to be established, and route transmission may be affected.";
            }
            leaf isIgnore {
              type boolean;
              default "false";
              description
                "Tear down sessions between peers and clear all related routing information. By default, this function is disabled.";
            }
            leaf localIfName {
              type leafref {
                path "/ifm:ifm/ifm:interfaces/ifm:interface/ifm:ifName";
              }
              description
                "Name of a source interface that sends BGP packets. By default, the outbound interface of a BGP packet serves as the source interface of a BGP packet. To ensure that a router can send BGP packets when a physical interface fails, you can configure the source interface that sends BGP packets as a loopback interface. When using the loopback interface as the source interface, note the following points:
1. The address of the loopback interface of the BGP peer must be reachable.
2. For an EBGP connection, configure the maximum number of hops and allow EBGP peer relationships to be established in indirect mode.";
              ext:allowDelete "true";
            }
            leaf localIfAddress {
              type inet:ip-address-no-zone;
              description
                "Name of a source interface that sends BGP packets. By default, the outbound interface of a BGP packet serves as the source interface of a BGP packet. To ensure that a router can send BGP packets when a physical interface fails, you can configure the source interface that sends BGP packets as a loopback interface. When using the loopback interface as the source interface, note the following points:
1. The address of the loopback interface of the BGP peer must be reachable.
2. For an EBGP connection, configure the maximum number of hops and allow EBGP peer relationships to be established in indirect mode.";
              ext:allowDelete "true";
            }
            leaf ebgpMaxHop {
              type uint32 {
                range "1..255";
              }
              must "not(../validTtlHops>=1 and ../validTtlHops<=255) or (../validTtlHops>=1 and ../validTtlHops<=255 and ../ebgpMaxHop=1)";
              description
                "Maximum number of hops in an indirect EBGP connection. By default, EBGP connections can be established only between directly connected peers. The function must be configured on both ends.";
              ext:allowDelete "true";
            }
            leaf validTtlHops {
              type uint16 {
                range "1..255";
              }
              must "not(../ebgpMaxHop and ../ebgpMaxHop>1 and ../ebgpMaxHop<=255)";
              description
                "Enable GTSM on a peer or peer group. The valid-TTL-Value parameter is used to specify the number of TTL hops to be detected. If the value is configured as hops, the valid TTL range of the detected packet is [255-hops+1, 255]. ";
              ext:allowDelete "true";
            }
            leaf connectMode {
              type bgpcommPeerConnectMode;
              default "null";
              description
                "The value can be Connect-only, Listen-only, or Both. If the value is Connect-only, the specified peer or peer group only initiatively sends connection requests, instead of listening to connection requests. If the value is Listen-only, the specified peer or peer group only listens to connection requests, instead of initiatively sending connection requests. If the value is Both, the specified peer or peer group not only initiatively sends connection requests, but also listens to connection requests. The default value is Both.";
              ext:allowDelete "true";
            }
            leaf isLogChange {
              type boolean;
              default "true";
              description
                "Enable BGP to record the session status and events of the specified peer or peer group. By default, the function is enabled.";
            }
            leaf pswdType {
              type bgpcommPasswordType;
              must "not(../pswdType and ../pswdType!='null' and ../keyChainName)";
              default "null";
              description
                "Enable BGP peers to establish a TCP connection and perform the Message Digest 5 (MD5) authentication for BGP messages. Plaintexts and ciphertexts are supported.";
              ext:allowDelete "true";
            }
            leaf pswdCipherText {
              when "not(not(../pswdType))";
              type pub-type:passwordExtend;
              description
                "Enable BGP peers to establish a TCP connection and perform the Message Digest 5 (MD5) authentication for BGP messages. The character string in a password identifies the contents of the password, spaces not supported. The TCP connection can be established only when the same MD5 authentication password is set on both ends. If a plaintext is used, the maximum password length is 255. If a ciphertext is used, the maximum password length is 432. If the length is set to 0, no password is set.";
              ext:allowDelete "true";
            }
            leaf keepAliveTime {
              type uint32 {
                range "0..21845";
              }
              default "60";
              description
                "Specify the Keepalive time of a peer or peer group. The value is an integer, in seconds. If the value of a timer changes, the peers need to re-negotiate the interval value for the keepalive-time and hold-time. This disconnects the BGP peer relationship between the routers. Therefore, you need to double check whether it is a must to change the value of the timer. Ensure that the hold time is at least three times longer than the keepalive time when you configure the BGP timer.";
              ext:allowDelete "true";
            }
            leaf holdTime {
              type uint32 {
                range "0..65535";
              }
              must "(../holdTime!=1) and (../holdTime!=2) and (../holdTime>=../keepAliveTime*3) and (../holdTime>=../minHoldTime)";
              default "180";
              description
                "Specify the Hold time of a peer or peer group. The value is either 0 or an integer ranging from 0 to 65535, in seconds. When setting the timer values of keepalive-time and hold-time, avoid the following settings: 1.The interval values of keepalive-time and hold-time are both set to 0. This will cause BGP timer to become invalid, and BGP will not detect link faults based on the timer. 
2. The interval value of hold-time is much greater than that of keepalive-time. For example, the interval value of keepalive-time is 1, and that of hold-time is 65535. If the interval value of hold-time is too large, BGP will not be able to detect link faults in time. The priority of the timer configured here is lower than that of timer configured with interval values of keepalive-time and hold-time of a peer. After a connection is established between peers, the interval values of keepalive-time and hold-time are negotiated by the peers. The smaller interval value of hold-time contained in Open packets of both peers is taken as the interval value of hold-time. The smaller interval value of one third of the interval value of hold-time and the locally set interval value of keepalive-time is taken as the interval value of keepalive-time.";
              ext:allowDelete "true";
            }
            leaf minHoldTime {
              type uint32 {
                range "0..65535";
              }
              default "0";
              description
                "The minimum hold time is either 0 or an integer ranging from 20 to 65535, in seconds. If the value is changed, the new value takes effect since the next peer relationship establishment. During the peer relationship establishment, the local device checks the hold time of the remote end. If the hold time is less than the minimum hold time, the local device sends an error packet with error code 02 and subcode 06, and the peer relationship fails to be established.

";
              ext:allowDelete "true";
            }
            leaf keyChainName {
              type string {
                length "1..47";
              }
              must "not(../pswdType and ../pswdType!='null' and ../keyChainName)";
              description
                "Specify the Keychain authentication name used when BGP peers establish a TCP connection. The value is a string, spaces not supported. By default, the Keychain authentication is not configured. Keychain authentication mode and password authentication mode are mutually exclusive. Configuring Keychain authentication can enhance the security of the TCP connections between BGP peers. Keychain authentication using the same encryption algorithm and password must be configured on the two ends of BGP peers to establish a TCP connection and exchange BGP packets. Before configuring BGP Keychain authentication, you need to configure Keychain according to keychain name. Otherwise, the TCP connections between the BGP peers cannot be established.";
              ext:allowDelete "true";
            }
            leaf pathMTUD {
              type boolean;
              default "false";
              description
                "path-mtu auto-discovery.";
            }
            leaf trackingEnable {
              type boolean;
              default "false";
              description
                "Enable peer tracking, After peer tracking is enabled, the device can fast detect the unreachability of a peer and reset the session.";
              ext:allowDelete "true";
            }
            leaf trackDelayTime {
              when "../trackingEnable='true'";
              type uint16 {
                range "0..65535";
              }
              default "0";
              description
                "Specify the delay to reset the session, in seconds.";
              ext:allowDelete "true";
            }
            leaf connRetryTime {
              type uint16 {
                range "1..65535";
              }
              default "32";
              description
                "ConnectRetry interval. The value is an integer, in seconds. The default value is 32s.";
              ext:allowDelete "true";
            }
            leaf tcpMSS {
              type uint16 {
                range "176..4096";
              }
              description
                "Maximum TCP MSS value used for TCP connection establishment for a peer. ";
              ext:allowDelete "true";
            }
            leaf mplsLocalIfnetDisable {
              when "../../../vrfName='_public_'";
              type boolean;
              default "false";
              description
                "Disable MPLS local IFNET tunnel creation. By default, MPLS local IFNET tunnels can be created.";
              ext:allowDelete "true";
            }
            leaf prependGlobalAs {
              when "not(not(../fakeAs))";
              type boolean;
              default "false";
              description
                "Add the global AS number to the Update packets to be advertised.";
            }
            leaf prependFakeAs {
              when "not(not(../fakeAs))";
              type boolean;
              default "false";
              description
                "Add the Fake AS number to received Update packets.";
            }
            leaf pathAttrDiscardIdMap {
              type pub-type:id-range {
                ext:value-range '1..255';
                pattern '((2[0-5][0-5]|1[0-9][0-9]|[1-9][0-9]|[1-9])?(-(2[0-5][0-5]|1[0-9][0-9]|[1-9][0-9]|[1-9]))?(,((2[0-5][0-5]|1[0-9][0-9]|[1-9][0-9]|[1-9])(-(2[0-5][0-5]|1[0-9][0-9]|[1-9][0-9]|[1-9]))?))*)|((([\+|\-](2[0-5][0-5]|1[0-9][0-9]|[1-9][0-9]|[1-9]))|([\+|\-]\((2[0-5][0-5]|1[0-9][0-9]|[1-9][0-9]|[1-9])-(2[0-5][0-5]|1[0-9][0-9]|[1-9][0-9]|[1-9])\)))?(,(([\+|\-](2[0-5][0-5]|1[0-9][0-9]|[1-9][0-9]|[1-9]))|([\+|\-]\((2[0-5][0-5]|1[0-9][0-9]|[1-9][0-9]|[1-9])-(2[0-5][0-5]|1[0-9][0-9]|[1-9][0-9]|[1-9])\))))*)';
              }
              description
                "Specify a discard attrId list.The format of a list is as follows:20-30,55.No support the attribute ids as follows:
IBGP peer or CONFEDERATION EBGP peer or CONFEDERATION IBGP peer: 1(ORIGIN),2(AS_PATH),3(NEXT_HOP),4(MED),5(LOCALPREF),8(COMMUNITY),9(ORIGINATOR),10(CLUSTER-ID),14(MP_NLRI),15(MP_UNLRI),16(EXTCOMMUNITY),
EBGP peer: 1(ORIGIN),2(AS_PATH),3(NEXT_HOP),4(MED),8(COMMUNITY),14(MP_NLRI),15(MP_UNLRI),16(EXTCOMMUNITY)";
              ext:allowDelete "true";
            }
            leaf pathAttrWithdrawIdMap {
              type pub-type:id-range {
                ext:value-range '1..255';
                pattern '((2[0-5][0-5]|1[0-9][0-9]|[1-9][0-9]|[1-9])?(-(2[0-5][0-5]|1[0-9][0-9]|[1-9][0-9]|[1-9]))?(,((2[0-5][0-5]|1[0-9][0-9]|[1-9][0-9]|[1-9])(-(2[0-5][0-5]|1[0-9][0-9]|[1-9][0-9]|[1-9]))?))*)|((([\+|\-](2[0-5][0-5]|1[0-9][0-9]|[1-9][0-9]|[1-9]))|([\+|\-]\((2[0-5][0-5]|1[0-9][0-9]|[1-9][0-9]|[1-9])-(2[0-5][0-5]|1[0-9][0-9]|[1-9][0-9]|[1-9])\)))?(,(([\+|\-](2[0-5][0-5]|1[0-9][0-9]|[1-9][0-9]|[1-9]))|([\+|\-]\((2[0-5][0-5]|1[0-9][0-9]|[1-9][0-9]|[1-9])-(2[0-5][0-5]|1[0-9][0-9]|[1-9][0-9]|[1-9])\))))*)';
              }
              description
                "Specify a withdraw attrId list.The format of a list is as follows:20-30,55.No support the attribute ids as follows:
IBGP peer or CONFEDERATION EBGP peer or CONFEDERATION IBGP peer: 1(ORIGIN),2(AS_PATH),3(NEXT_HOP),4(MED),5(LOCALPREF),8(COMMUNITY),9(ORIGINATOR),10(CLUSTER-ID),14(MP_NLRI),15(MP_UNLRI),16(EXTCOMMUNITY),
EBGP peer: 1(ORIGIN),2(AS_PATH),3(NEXT_HOP),4(MED),8(COMMUNITY),14(MP_NLRI),15(MP_UNLRI),16(EXTCOMMUNITY)";
              ext:allowDelete "true";
            }
            leaf checkFirstAs {
              type bgpCheckFirstAsTriState;
              default "default";
              description
                "Check the first AS in the AS_Path of the update messages from EBGP peers. By default, this function is enabled.";
            }
            container peerLogInfos {
              config false;
              description
                "Peer log information list.";
              list peerLogInfo {
                key "logIndex";
                config false;
                description
                  "Peer log information. After the log function is enabled on a peer, you can check the recorded log information about the peer.";
                leaf logIndex {
                  type uint32;
                  config false;
                  description
                    "Index of peer log information.";
                }
                leaf stateEvent {
                  type string {
                    length "1..20";
                  }
                  config false;
                  description
                    "Status of a peer when an event occurs.";
                }
                leaf errorCode {
                  type uint8 {
                    range "0..255";
                  }
                  config false;
                  description
                    "Error code that triggers an event.";
                }
                leaf errorSubCode {
                  type uint8 {
                    range "0..255";
                  }
                  config false;
                  description
                    "Error subcode that triggers an event.";
                }
                leaf notification {
                  type string {
                    length "1..40";
                  }
                  config false;
                  description
                    "Sent or received notification messages.";
                }
                leaf logDateTime {
                  type yang:date-and-time;
                  config false;
                  description
                    "Time when the log information was recorded.";
                }
              }
            }
            container peerBfd {
              description
                "Configure BFD.";
              leaf isBfdBlock {
                type boolean;
                default "false";
                description
                  "Prevent  a BGP peer from inheriting the BFD configuration of the BGP peer group.";
              }
              leaf multiplier {
                type uint32 {
                  range "3..50";
                }
                default "3";
                description
                  "Specify the detection multiplier. The default value is 3.";
                ext:allowDelete "true";
              }
              leaf isBfdEnable {
                type boolean;
                default "false";
                description
                  "Enable BFD.";
              }
              leaf rxInterval {
                type uint32 {
                  range "3..1000";
                }
                description
                  "Specify the minimum interval at which BFD packets are received. By default, the value is determined by the PAF file.";
                ext:allowDelete "true";
              }
              leaf txInterval {
                type uint32 {
                  range "3..1000";
                }
                description
                  "Specify the minimum interval at which BFD packets are sent. By default, the value is determined by the PAF file.";
                ext:allowDelete "true";
              }
              leaf isSingleHop {
                when "../isBfdEnable='true'";
                type boolean;
                default "false";
                description
                  "The single hop mode is preferred during the BFD session establishment between IBGP peers.";
              }
              leaf bfdCompatible {
                when "../isBfdEnable='true'";
                type boolean;
                default "false";
                description
                  "Compatible.";
              }
              leaf perLinkEcho {
                when "../isBfdEnable='true'";
                type boolean;
                must "../isSingleHop='false' and ../bfdCompatible='false' and ../isBfdEnable='true' or (not(../isSingleHop='false' and ../bfdCompatible='false' and ../isBfdEnable='true') and ../perLinkEcho='false')";
                default "false";
                description
                  "The per-link one-arm-echo mode is preferred during the BFD session establishment between IBGP peers.";
              }
            }
          }
        }
        container bgpVrfAFs {
          description
            "List of BGP address family instances.";
          list bgpVrfAF {
            key "afType";
            description
              "BGP address family instance.";
            leaf afType {
              type bgpcommPrefixType;
              must "(../../../vrfName='_public_' and (../afType='ipv4uni' or ../afType='ipv4multi' or ../afType='ipv4vpn' or ../afType='ipv6uni' or ../afType='ipv6vpn' or ../afType='ipv4flow' or ../afType='ipv6flow' or ../afType='l2vpnad' or ../afType='mvpn' or ../afType='evpn' or ../afType='ipv4vpnmcast' or ../afType='mdt' or ../afType='ls' or ../afType='vpntarget' or ../afType='vpnv4flow' or ../afType='vpnv6flow' or ../afType='ipv4labeluni' or ../afType='mvpnv6' or ../afType='rpd') ) or ((not(../../../vrfName='_public_') and (../afType='ipv4uni' or ../afType='ipv6uni' or ../afType='ipv4flow' or ../afType='ipv6flow' or ../afType='ipv4labeluni') ))";
              description
                "Address family type of a BGP instance. ";
            }
            leaf vrfAsNum {
              when "../../../vrfName!='_public_' and ../afType!='ipv4flow' and ../afType!='ipv6flow' and ../afType!='ipv4labeluni'";
              type asNumberValidate;
              description
                "Specify the unique AS number for the vpn instance";
              ext:allowDelete "true";
            }
            leaf maxLoadIbgpNum {
              when "not(../afType='evpn' or ../afType='ipv4flow' or ../afType='ipv4labeluni' or ../afType='ipv4vpn' or ../afType='ipv4vpnmcast' or ../afType='ipv6flow' or ../afType='ipv6vpn' or ../afType='l2vpnad' or ../afType='ls' or ../afType='mdt' or ../afType='mvpn' or ../afType='mvpnv6' or ../afType='rpd' or ../afType='vpntarget' or ../afType='vpnv4flow' or ../afType='vpnv6flow') or ../afType='ipv4uni' or ../afType='ipv6uni'";
              type uint16 {
                range "1..65535";
              }
              default "1";
              description
                "Specify the maximum number of equal-cost IBGP routes. By default, the value is 1. ";
              ext:allowDelete "true";
            }
            leaf ibgpEcmpNexthopChanged {
              when "not(../../../vrfName='_public_' and ../afType='l2vpnad' or ../afType='evpn' or ../afType='ipv4flow' or ../afType='ipv4labeluni' or ../afType='ipv4vpn' or ../afType='ipv4vpnmcast' or ../afType='ipv6flow' or ../afType='ipv6vpn' or ../afType='l2vpnad' or ../afType='ls' or ../afType='mdt' or ../afType='mvpn' or ../afType='mvpnv6' or ../afType='rpd' or ../afType='vpntarget' or ../afType='vpnv4flow' or ../afType='vpnv6flow') or ../afType='ipv4uni' or ../afType='ipv6uni'";
              type boolean;
              must "../maxLoadIbgpNum and ../maxLoadIbgpNum>1 or (not(../maxLoadIbgpNum and ../maxLoadIbgpNum>1) and ../ibgpEcmpNexthopChanged='false')";
              default "false";
              description
                "When equal-cost IBGP routes are load-balancing traffic, the next hop of these routes is changed to a local interface before these routes are advertised. By default, this function is not enabled. This function can be enabled only when the maximum number of equal-cost IBGP routes is greater than 1.";
            }
            leaf maxLoadEbgpNum {
              when "not(../afType='evpn' or ../afType='ipv4flow' or ../afType='ipv4labeluni' or ../afType='ipv4vpn' or ../afType='ipv4vpnmcast' or ../afType='ipv6flow' or ../afType='ipv6vpn' or ../afType='l2vpnad' or ../afType='ls' or ../afType='mdt' or ../afType='mvpn' or ../afType='mvpnv6' or ../afType='rpd' or ../afType='vpntarget' or ../afType='vpnv4flow' or ../afType='vpnv6flow') or ../afType='ipv4uni' or ../afType='ipv6uni'";
              type uint16 {
                range "1..65535";
              }
              default "1";
              description
                "Specify the maximum number of equal-cost EBGP routes. By default, the value is 1.";
              ext:allowDelete "true";
            }
            leaf ebgpEcmpNexthopChanged {
              when "not(../../../vrfName='_public_' and ../afType='l2vpnad' or ../afType='evpn' or ../afType='ipv4flow' or ../afType='ipv4labeluni' or ../afType='ipv4vpn' or ../afType='ipv4vpnmcast' or ../afType='ipv6flow' or ../afType='ipv6vpn' or ../afType='l2vpnad' or ../afType='ls' or ../afType='mdt' or ../afType='mvpn' or ../afType='mvpnv6' or ../afType='rpd' or ../afType='vpntarget' or ../afType='vpnv4flow' or ../afType='vpnv6flow') or ../afType='ipv4uni' or ../afType='ipv6uni'";
              type boolean;
              must "../maxLoadEbgpNum and ../maxLoadEbgpNum>1 or (not(../maxLoadEbgpNum and ../maxLoadEbgpNum>1) and ../ebgpEcmpNexthopChanged='false')";
              default "false";
              description
                "When equal-cost EBGP routes are load-balancing traffic, the next hop of these routes is changed to a local interface before these routes are advertised. By default, this function is not enabled. This function can be enabled only when the maximum number of equal-cost EBGP routes is greater than 1.";
            }
            leaf maximumLoadBalance {
              when "not(../afType!='ipv4uni' and ../afType!='ipv4multi' and ../afType!='ipv6uni' or ../afType='ipv4flow' or ../afType='ipv4labeluni' or ../afType='ipv4vpnmcast' or ../afType='ipv6flow' or ../afType='ls' or ../afType='mdt' or ../afType='rpd' or ../afType='vpntarget' or ../afType='vpnv4flow' or ../afType='vpnv6flow')";
              type uint16 {
                range "1..65535";
              }
              default "1";
              description
                "Specify the maximum number of equal-cost routes in the BGP routing table. The value can be 1 or an integer greater than 1. The value depends on the associated license. By default, the maximum number of equal-cost routes is 1. Equal-cost BGP routes can be generated for load balancing only when the BGP routes meet the first nine rules of the route-selection policy and have the same AS-Path attribute.";
              ext:allowDelete "true";
            }
            leaf ecmpNexthopChanged {
              when "not(../../../vrfName='_public_' and ../afType='l2vpnad' or ../afType='evpn' or ../afType='ipv4flow' or ../afType='ipv4labeluni' or ../afType='ipv4vpn' or ../afType='ipv4vpnmcast' or ../afType='ipv6flow' or ../afType='ipv6vpn' or ../afType='l2vpnad' or ../afType='ls' or ../afType='mdt' or ../afType='mvpn' or ../afType='mvpnv6' or ../afType='rpd' or ../afType='vpntarget' or ../afType='vpnv4flow' or ../afType='vpnv6flow') or ../afType='ipv4uni' or ../afType='ipv6uni'";
              type boolean;
              must "../maximumLoadBalance and ../maximumLoadBalance>1 or (not(../maximumLoadBalance and ../maximumLoadBalance>1) and ../ecmpNexthopChanged='false')";
              default "false";
              description
                "When equal-cost BGP routes are load-balancing traffic, the next hop of these routes is changed to a local interface before these routes are advertised. By default, this function is not enabled. This function can be enabled only when the maximum number of equal-cost BGP routes is greater than 1.";
            }
            leaf eibgpLoadBalan {
              when "not(../afType='ipv4labeluni' or ../afType='ipv4vpnmcast' or ../afType='ls' or ../afType='mdt' or ../afType='rpd' or ../afType='vpntarget' or ../afType='vpnv4flow' or ../afType='vpnv6flow') or ../../../vrfName!='_public_' and ../afType!='ipv4flow' and ../afType!='ipv6flow' and ../afType!='ipv4labeluni'";
              type uint16 {
                range "1..65535";
              }
              description
                "Specify the maximum number of equal-cost EBGP routes and IBGP routes. After the attribute is set, load balancing is performed among equal-cost BGP VPN routes, regardless of the route type, EBGP or IBGP. By default, the maximum number of equal-cost EBGP routes and IBGP routes is 0.";
              ext:allowDelete "true";
            }
            leaf eibgpEcmpNexthopChanged {
              when "not(../afType='ls' or ../afType='rpd' or ../afType='vpnv4flow' or ../afType='vpnv6flow') or ../../../vrfName!='_public_' and ../afType!='ipv4flow' and ../afType!='ipv6flow' and ../afType!='ipv4labeluni'";
              type boolean;
              must "../eibgpLoadBalan and ../eibgpLoadBalan>0 or (not(../eibgpLoadBalan and ../eibgpLoadBalan>0) and ../eibgpEcmpNexthopChanged='false')";
              default "false";
              description
                "When equal-cost EBGP and IBGP routes are load-balancing traffic, the next hop of these routes is changed to a local interface before these routes are advertised. By default, this function is not enabled. ";
            }
            leaf defaultLocalPref {
              when "not(../afType='evpn' or ../afType='ipv4flow' or ../afType='ipv4vpnmcast' or ../afType='ipv6flow' or ../afType='ls' or ../afType='mdt' or ../afType='mvpn' or ../afType='mvpnv6' or ../afType='rpd' or ../afType='vpnv4flow' or ../afType='vpnv6flow')";
              type uint32 {
                range "0..4294967295";
              }
              default "100";
              description
                "Set the Local-Preference attribute. The value is an integer. The greater the value, the higher the priority. By default, the Local-Preference for BGP is 100. Setting different Local-Preferences affects BGP route selection. When a router that runs BGP has multiple routes to the same destination, the router selects the route with the highest Local-Preference. The Local-Preference is exchanged only between IBGP peers and is not advertised to other ASs.";
              ext:allowDelete "true";
            }
            leaf defaultMed {
              when "not(../afType='evpn' or ../afType='ipv4flow' or ../afType='ipv4vpnmcast' or ../afType='ipv6flow' or ../afType='l2vpnad' or ../afType='ls' or ../afType='mdt' or ../afType='mvpn' or ../afType='mvpnv6' or ../afType='rpd' or ../afType='vpnv4flow' or ../afType='vpnv6flow')";
              type uint32 {
                range "0..4294967295";
              }
              description
                "Specify the Multi-Exit-Discriminator (MED) of BGP routes. The value is an integer. By default, the MED is 0. This value is valid only for the imported routes and BGP summarized routes on the local router.
";
              ext:allowDelete "true";
            }
            leaf defaultRtImportEnable {
              when "not(../afType='ipv4vpnmcast' or ../afType='ls' or ../afType='mdt' or ../afType='rpd' or ../afType='vpntarget' or ../afType='vpnv4flow' or ../afType='vpnv6flow') or ../afType!='ipv6vpn' and ../afType!='ipv4vpn' and ../afType!='ipv4flow' and ../afType!='ipv6flow' and ../afType!='mvpn' and ../afType!='mvpnv6' and ../afType!='l2vpnad' and ../afType!='evpn' and ../afType!='ipv4vpnmcast' and ../afType!='mdt' and ../afType!='ls' and ../afType!='rpd' and ../afType!='vpntarget'";
              type boolean;
              default "false";
              description
                "Import default routes into the BGP routing table. By default, BGP does not add default routes to the BGP routing table. default-route-imported must be used with import-routes so that default routes can be imported to the BGP routing table. If only import-routes is used, no default routes can be added to the BGP routing table. In addition, default-route-imported can only import the default routes in the routing table into the BGP routing table.";
            }
            leaf routeMatchDestination {
              when "not(../afType!='ipv4flow' and ../afType!='ipv6flow' or ../afType='ipv4vpnmcast' or ../afType='mdt' or ../afType='rpd' or ../afType='vpntarget' or ../afType='vpnv4flow' or ../afType='vpnv6flow')";
              type boolean;
              default "false";
              description
                "Match the route destination.";
            }
            leaf routerId {
              when "not(../../../vrfName!='_public_' and ../afType='ipv4flow' or ../../../vrfName!='_public_' and ../afType='ipv6flow' or ../afType='ipv4vpnmcast' or ../afType='ls' or ../afType='mdt' or ../afType='rpd' or ../afType='vpntarget' or ../afType='vpnv4flow' or ../afType='vpnv6flow') or ../../../vrfName!='_public_' and ../afType!='ipv4flow' and ../afType!='ipv6flow' and ../afType!='ipv4labeluni'";
              type inet:ipv4-address-no-zone;
              description
                "ID of a router that is in IPv4 address format. Certain dynamic routing protocols require a router ID. If no router ID is specified for a router when these protocols are enabled, the router ID in the RM module is used by default. The default router ID in the RM module is 0.0.0.0 when the router is not configured with any interface. 
The rules for selecting a router ID are as follows:
1. If you set a router ID through this configuration, the set router ID is used. If the router ID is not set, you need to select a router ID according to the following rules:
(1) If loopback interfaces configured with IP addresses exist, the largest IP address among the IP addresses of the loopback interfaces is selected as the router ID.
(2) If no loopback interface configured with an IP address exists, the largest IP address among the IP addresses of other interfaces is selected as the router ID, regardless of whether the interface is Up.
The router ID is reselected only when the interface address that is selected as the router ID is deleted or changed. The router ID is not reselected in any of the following cases:
a. The interface is Down.
b. A loopback interface is configured when the IP address of a non-loopback interface is selected as the router ID.
c. A larger IP address of an interface is configured.
2. Each VPN instance selects the router ID from the addresses of the interfaces of the VPN instance according to the preceding rules.
3. When both the AMB and SMB exist on the router, the system backs up the router ID set through the related command and the router ID that is selected from IP addresses of the interfaces. After the active/standby switchover is performed, the system checks the validity of the router ID selected from the interface addresses. If the router ID is invalid, the system reselects a router ID.";
              ext:allowDelete "true";
            }
            leaf vrfRidAutoSel {
              when "not(../afType='ipv4flow' or ../afType='ipv4vpnmcast' or ../afType='ipv6flow' or ../afType='ls' or ../afType='mdt' or ../afType='rpd' or ../afType='vpntarget' or ../afType='vpnv4flow' or ../afType='vpnv6flow') or ../../../vrfName!='_public_' and ../afType!='ipv4flow' and ../afType!='ipv6flow' and ../afType!='ipv4labeluni'";
              type boolean;
              default "false";
              description
                "By default, a BGP VPN instance does not automatically select a router ID. If a BGP VPN instance is not enabled to select a router ID, a router ID can be configured for the BGP VPN instance. If no router ID is configured for the BGP VPN instance, the BGP VPN instance inherits the router ID of the public network instance. If a BGP VPN instance is enabled to select a router ID, it uses the address of an interface bound to a VPN as the router ID based on the following rules: 
1. If Loopback interfaces configured with IP addresses exist, the largest IP address among the IP addresses of the Loopback interfaces is selected as the router ID. 
2. If there is no Loopback interface configured with an IP address, the largest IP address among the IP addresses of other interfaces is selected as the router ID, regardless of whether the interface is Up.";
            }
            leaf nexthopThirdParty {
              when "not(../afType='ipv4vpnmcast' or ../afType='mdt' or ../afType='rpd' or ../afType='vpntarget' or ../afType='vpnv4flow' or ../afType='vpnv6flow') or ../afType='ipv4uni'";
              type boolean;
              default "false";
              description
                "Enable BGP third-party next hop.";
            }
            leaf summaryAutomatic {
              when "not(../afType!='ipv4uni' and ../afType!='ipv4multi' or ../afType='ipv4labeluni' or ../afType='ipv4vpnmcast' or ../afType='ls' or ../afType='mdt' or ../afType='rpd' or ../afType='vpntarget' or ../afType='vpnv4flow' or ../afType='vpnv6flow')";
              type boolean;
              default "false";
              description
                "Enable automatic summarization for imported routes. By default, the locally imported routes are not summarized automatically. Manual summarization takes precedence over automatic summarization. After automatic summarization is enabled, BGP summarizes routes based on the natural network segment (for example, 10.1.1.1/24 and 10.2.1.1/24 are summarized into 10.0.0.0/8, a Class A address), and sends only the summarized route to peers. This reduces the number of routes.";
            }
            leaf autoFrrEnable {
              when "not(../afType='vpnv4flow' or ../afType='vpnv6flow') or ../afType!='ipv4multi' and ../afType!='ipv4flow' and ../afType!='ipv6flow' and ../afType!='ipv6vpn' and ../afType!='l2vpnad' and ../afType!='mvpn' and ../afType!='ipv4vpnmcast' and ../afType!='mdt' and ../afType!='ls' and ../afType!='rpd' and ../afType!='vpntarget' and ../afType!='mvpnv6'";
              type boolean;
              default "false";
              description
                "Enable BGP Auto FRR. By default, BGP Auto FRR is disabled. If IP FRR, VPN FRR, and Auto FRR are all enabled, IP FRR and VPN FRR take precedence over Auto FRR. If a route fails to match the routing policy of IP FRR or VPN FRR, Auto FRR takes effect.";
            }
            leaf domainAs {
              when "not(../afType='rpd' or ../afType='vpnv4flow' or ../afType='vpnv6flow') or ../afType='ls'";
              type asNumberValidate;
              description
                "Domain AS.";
              ext:allowDelete "true";
            }
            leaf domainIdentifier {
              when "not(../afType='rpd' or ../afType='vpnv4flow' or ../afType='vpnv6flow') or ../afType='ls'";
              type inet:ip-address-no-zone;
              description
                "Domain ID.";
              ext:allowDelete "true";
            }
            leaf bwBcNonstd {
              when "not(../afType='rpd' or ../afType='vpnv4flow' or ../afType='vpnv6flow') or ../afType='ls'";
              type boolean;
              default "false";
              description
                "BGP-LS advertise and parse Bandwidth BC";
            }
            leaf loadBalancingIgpMetricIgnore {
              when "../afType='ipv4uni' or ../afType='ipv6uni' or (../../../vrfName='_public_' and ../afType='ipv4labeluni')";
              type boolean;
              default "false";
              description
                "Configure BGP to ignore the IGP cost of each BGP route to the next hop when selecting routes for load balancing. By default, only the routes with the same IGP cost can participate in load balancing.";
            }
            leaf loadBalancingEibgp {
              when "not(../afType='ipv4flow' or ../afType='ipv4labeluni' or ../afType='ipv4vpnmcast' or ../afType='ipv6flow' or ../afType='mdt' or ../afType='rpd' or ../afType='vpntarget' or ../afType='vpnv4flow' or ../afType='vpnv6flow') or ../../../vrfName!='_public_' and ../afType!='ipv4flow' and ../afType!='ipv6flow'";
              type boolean;
              default "false";
              description
                "Configure EIBGP route load balancing. By default, load balancing cannot be implemented among IBGP and EBGP routes.";
            }
            leaf loadBalancingAsPathIgnore {
              when "../afType='ipv4uni' or ../afType='ipv6uni' or (../../../vrfName='_public_' and ../afType='ipv4labeluni')";
              type boolean;
              must "not((../asPathNeglect='true' or ../loadBalancingAsPathRelax='true') and ../loadBalancingAsPathIgnore='true')";
              default "false";
              description
                "Configure BGP to ignore the AS_Path of each BGP route to the next hop when selecting routes for load balancing. By default, only the routes with the same AS_Path can participate in load balancing.";
            }
            leaf loadBalancingAsPathRelax {
              when "../afType='ipv4uni' or ../afType='ipv6uni' or (../../../vrfName='_public_' and ../afType='ipv4labeluni')";
              type boolean;
              must "not(../loadBalancingAsPathRelax='true' and ../loadBalancingAsPathIgnore='true')";
              default "false";
              description
                "Configure BGP to ignore comparison of AS_Path attributes with the same length. By default, only the routes with the same AS_Path can participate in load balancing.";
            }
            leaf vplsEnable {
              when "not(../afType!='l2vpnad' or ../afType='ipv4vpnmcast' or ../afType='mdt' or ../afType='rpd' or ../afType='vpntarget' or ../afType='vpnv4flow' or ../afType='vpnv6flow')";
              type boolean;
              default "false";
              description
                "Enable Virtual Private LAN Services";
            }
            leaf multiHomingNonStdEnable {
              when "not(../afType!='l2vpnad' or ../afType='ipv4vpnmcast' or ../afType='mdt' or ../afType='rpd' or ../afType='vpnv4flow' or ../afType='vpnv6flow')";
              type boolean;
              default "false";
              description
                "Enable capability of multi-homing for Virtual Private LAN Services ";
            }
            leaf vplsAdDisable {
              when "not(../afType!='l2vpnad' or ../afType='ipv4vpnmcast' or ../afType='mdt' or ../afType='rpd' or ../afType='vpntarget' or ../afType='vpnv4flow' or ../afType='vpnv6flow')";
              type boolean;
              default "false";
              description
                "Enable Virtual private LAN service auto-discovery.Not receive BGP-AD Route.";
            }
            leaf vpwsEnable {
              when "not(../afType!='l2vpnad')";
              type boolean;
              default "false";
              description
                "Enable Virtual Private Wire Services";
            }
            leaf medPlusIgp {
              when "not(../afType='rpd' or ../afType='vpntarget' or ../afType='vpnv4flow' or ../afType='vpnv6flow') or ../afType!='ipv4flow' and ../afType!='ipv6flow' and ../afType!='mdt' and ../afType!='l2vpnad' and ../afType!='mvpn' and ../afType!='mvpnv6' and ../afType!='evpn' and ../afType!='ipv4vpnmcast' and ../afType!='ls' and ../afType!='rpd' and ../afType!='vpntarget' and ../afType!='vpnv4flow' and ../afType!='vpnv6flow' and ../igpMetricIgnore='false'";
              type boolean;
              default "false";
              description
                "add the IGP cost to the next-hop destination to the MED before comparing MED values for path selection.";
            }
            leaf activateTag {
              when "../afType='ipv4vpn'";
              type boolean;
              default "false";
              description
                "After the command is run, the tag attribute can be used in if-match clauses for filtering.";
            }
            leaf medMultiplier {
              when "not(../afType='rpd' or ../afType='vpnv4flow' or ../afType='vpnv6flow') or ../medPlusIgp='true'";
              type uint16 {
                range "1..1000";
              }
              default "1";
              description
                "Value of med product factor";
              ext:allowDelete "true";
            }
            leaf igpMultiplier {
              when "not(../afType='rpd' or ../afType='vpnv4flow' or ../afType='vpnv6flow') or ../medPlusIgp='true'";
              type uint16 {
                range "1..1000";
              }
              default "1";
              description
                "Value of igp cost product factor";
              ext:allowDelete "true";
            }
            leaf ribOnlyEnable {
              when "not(../../../vrfName!='_public_' and ../afType!='ipv4flow' and ../afType!='ipv6flow' or ../../../vrfName='_public_' and ../afType!='ipv4uni' and ../afType!='ipv6uni' and ../afType!='ipv4flow' and ../afType!='ipv6flow' or ../afType='ipv4labeluni' or ../afType='ipv4vpnmcast' or ../afType='mdt' or ../afType='rpd' or ../afType='vpntarget' or ../afType='vpnv4flow' or ../afType='vpnv6flow')";
              type boolean;
              must "not(../activeRouteAdvertise='true' and ../ribOnlyEnable='true')";
              default "false";
              description
                "Prevent BGP routes from being added to the IP routing table. By default, preferred BGP routes are added to the IP routing table.";
            }
            leaf ribOnlyPolicyName {
              when "not(../../../vrfName!='_public_' and ../afType!='ipv4flow' and ../afType!='ipv6flow' or ../../../vrfName!='_public_' and ../afType='ipv4flow' and ../ribOnlyEnable='true' or ../../../vrfName!='_public_' and ../afType='ipv6flow' and ../ribOnlyEnable='true' or ../../../vrfName='_public_' and ../afType!='ipv4multi' and ../afType!='ipv4labeluni' and ../afType!='ipv4vpn' and ../afType!='ipv6vpn' and ../afType!='l2vpnad' and ../afType!='mvpn' and ../afType!='evpn' and ../afType!='ls' and ../afType!='rpd' and ../ribOnlyEnable='false' or ../../../vrfName='_public_' and ../afType!='ipv4multi' and ../afType!='ipv4vpn' and ../afType!='ipv6vpn' and ../afType!='ipv4flow' and ../afType!='ipv6flow' and ../afType!='l2vpnad' and ../afType!='mvpn' and ../afType!='evpn' and ../afType!='mdt' and ../afType!='ls' and ../afType!='rpd' and ../ribOnlyEnable='true' or ../../../vrfName='_public_' and ../afType!='ipv4uni' and ../afType!='ipv6uni' and ../afType!='ipv4flow' and ../afType!='ipv6flow' or ../afType='ipv4flow' and ../ribOnlyEnable='false' or ../afType='ipv4labeluni' or ../afType='ipv4vpnmcast' or ../afType='ipv6flow' and ../ribOnlyEnable='false' or ../afType='mdt' or ../afType='vpntarget') or ../../../vrfName!='_public_' and ../afType='ipv4flow' and ../ribOnlyEnable='true' or ../../../vrfName!='_public_' and ../afType='ipv6flow' and ../ribOnlyEnable='true' or ../../../vrfName='_public_' and ../afType!='ipv4multi' and ../afType!='ipv4vpn' and ../afType!='ipv6vpn' and ../afType!='l2vpnad' and ../afType!='mvpn' and ../afType!='evpn' and ../afType!='mdt' and ../afType!='ls' and ../afType!='rpd' and ../afType!='vpntarget' and ../ribOnlyEnable='true' or ../ribOnlyEnable='true'";
              type leafref {
                path "/rtp:rtp/rtp:routePolicys/rtp:routePolicy/rtp:name";
              }
              description
                "Specify the name of a routing policy. When both rib-only-enable and rib-only-policy-name are used, the routes that match the routing policy are not added to the IP routing table. Conversely, the routes that do not match the routing policy are added to the IP routing table, and the attributes of these routes are not modified.";
              ext:allowDelete "true";
            }
            leaf activeRouteAdvertise {
              when "not(../afType='ipv4labeluni' or ../afType='ipv4vpnmcast' or ../afType='ls' or ../afType='mdt' or ../afType='rpd' or ../afType='vpntarget' or ../afType='vpnv4flow' or ../afType='vpnv6flow') or ../afType!='ipv4multi' and ../afType!='ipv4vpn' and ../afType!='ipv6vpn' and ../afType!='ipv4flow' and ../afType!='ipv6flow' and ../afType!='l2vpnad' and ../afType!='mvpn' and ../afType!='mvpnv6' and ../afType!='evpn' and ../afType!='ls' and ../afType!='rpd' and ../afType!='mdt' and ../afType!='vpntarget' and ../afType!='ipv4vpnmcast' and ../afType!='ipv4labeluni'";
              type boolean;
              must "not(../activeRouteAdvertise='true' and ../ribOnlyEnable='true')";
              default "false";
              description
                "Advertise the optimal routes in the RM module to peers.";
            }
            leaf asPathNeglect {
              when "not(../afType='ipv4vpnmcast' or ../afType='ls' or ../afType='mdt' or ../afType='rpd' or ../afType='vpntarget' or ../afType='vpnv4flow' or ../afType='vpnv6flow' or ../loadBalancingAsPathIgnore='true') or ../afType!='ipv6vpn' and ../afType!='ipv4vpn' and ../afType!='ipv4flow' and ../afType!='ipv6flow' and ../afType!='mvpn' and ../afType!='mvpnv6' and ../afType!='l2vpnad' and ../afType!='evpn' and ../afType!='ipv4vpnmcast' and ../afType!='mdt' and ../afType!='ls' and ../afType!='rpd' and ../afType!='vpntarget' or ../loadBalancingAsPathIgnore!='true' and ../afType!='ipv6vpn' and ../afType!='ipv4vpn' and ../afType!='ipv4flow' and ../afType!='ipv6flow' and ../afType!='mvpn' and ../afType!='mvpnv6' and ../afType!='l2vpnad' and ../afType!='evpn' and ../afType!='mdt' and ../afType!='ls' and ../afType!='rpd' and ../afType!='vpntarget' and ../afType!='ipv4vpnmcast' and ../afType!='vpnv4flow' and ../afType!='vpnv6flow'";
              type boolean;
              default "false";
              description
                "Configure BGP to ignore the AS_Path attribute when selecting the optimal route. By default, BGP uses the AS_Path attribute as one of route selection rules, and a route with a shorter AS_Path is preferred. After as-path-neglect is selected, BGP does not compare the AS_Path length.";
            }
            leaf medNoneAsMaximum {
              when "not(../afType='ipv4vpnmcast' or ../afType='ls' or ../afType='mdt' or ../afType='rpd' or ../afType='vpntarget' or ../afType='vpnv4flow' or ../afType='vpnv6flow') or ../afType!='ipv6vpn' and ../afType!='ipv4vpn' and ../afType!='ipv4flow' and ../afType!='ipv6flow' and ../afType!='mvpn' and ../afType!='mvpnv6' and ../afType!='l2vpnad' and ../afType!='evpn' and ../afType!='ipv4vpnmcast' and ../afType!='mdt' and ../afType!='ls' and ../afType!='rpd' and ../afType!='vpntarget'";
              type boolean;
              default "false";
              description
                "If a route does not carry MED, BGP considers its MED as the default value (0) during route selection. After med-none-as-maximum is selected, BGP considers its MED as the largest MED value (4294967295).";
            }
            leaf routerIdNeglect {
              when "not(../afType='rpd' or ../afType='vpnv4flow' or ../afType='vpnv6flow') or ../afType!='ipv6vpn' and ../afType!='ipv4vpn' and ../afType!='ipv4flow' and ../afType!='ipv6flow' and ../afType!='mvpn' and ../afType!='mvpnv6' and ../afType!='l2vpnad' and ../afType!='evpn' and ../afType!='ipv4vpnmcast' and ../afType!='mdt' and ../afType!='ls' and ../afType!='rpd' and ../afType!='vpntarget'";
              type boolean;
              default "false";
              description
                "Configure BGP to ignore router IDs when selecting the optimal route. Comparing router IDs is the last resort in route selection. This means that if one optimal route must be selected and no other parameters can be used to break the tie, router IDs can be used. If this option is selected, the first received route will be selected as the optimal route, and BGP will ignore the router ID and peer address in route selection.";
            }
            leaf igpMetricIgnore {
              when "not(../afType='ls' or ../afType='rpd' or ../afType='vpnv4flow' or ../afType='vpnv6flow') or ../afType!='ipv4flow' and ../afType!='ipv6flow' and ../afType!='l2vpnad' and ../afType!='mvpn' and ../afType!='mvpnv6' and ../afType!='evpn' and ../afType!='ipv4vpnmcast' and ../afType!='ls' and ../afType!='rpd' and ../afType!='vpntarget' and ../afType!='vpnv4flow' and ../afType!='vpnv6flow' and ../medPlusIgp='false'";
              type boolean;
              default "false";
              description
                "Configure BGP to ignore the IGP cost of each BGP route to the next hop in route selection. By default, a BGP route with a smaller IGP cost to the next hop is preferred.";
            }
            leaf alwaysCompareMed {
              when "not(../afType='ipv4vpnmcast' or ../afType='ls' or ../afType='mdt' or ../afType='rpd' or ../afType='vpntarget' or ../afType='vpnv4flow' or ../afType='vpnv6flow') or ../afType!='ipv6vpn' and ../afType!='ipv4vpn' and ../afType!='ipv4flow' and ../afType!='ipv6flow' and ../afType!='mvpn' and ../afType!='mvpnv6' and ../afType!='l2vpnad' and ../afType!='evpn' and ../afType!='ipv4vpnmcast' and ../afType!='mdt' and ../afType!='ls' and ../afType!='rpd' and ../afType!='vpntarget'";
              type boolean;
              default "false";
              description
                "Configure BGP to compare the MEDs of routes from peers in different ASs in route selection. By default, BGP does not compare the MEDs of routes from peers in different ASs. If there are multiple reachable routes to the same destination, the route with the smallest MED is preferred. Do not use this option unless different ASs use the same IGP and route selection mode.";
            }
            leaf determinMed {
              when "not(../afType='ipv4vpnmcast' or ../afType='ls' or ../afType='mdt' or ../afType='rpd' or ../afType='vpntarget' or ../afType='vpnv4flow' or ../afType='vpnv6flow') or ../afType!='ipv6vpn' and ../afType!='ipv4vpn' and ../afType!='ipv4flow' and ../afType!='ipv6flow' and ../afType!='mvpn' and ../afType!='mvpnv6' and ../afType!='l2vpnad' and ../afType!='evpn' and ../afType!='ipv4vpnmcast' and ../afType!='mdt' and ../afType!='ls' and ../afType!='rpd' and ../afType!='vpntarget'";
              type boolean;
              default "false";
              description
                "Enable deterministic MED so that the route selection result is relevant to the sequence in which routes are received.";
            }
            leaf popGo {
              when "not(../afType='ipv4vpnmcast' or ../afType='mdt' or ../afType='rpd' or ../afType='vpntarget' or ../afType='vpnv4flow' or ../afType='vpnv6flow') or ../../../vrfName='_public_' and ../afType!='ipv4multi' and ../afType!='ipv4vpn' and ../afType!='ipv6uni' and ../afType!='ipv6vpn' and ../afType!='ipv4flow' and ../afType!='ipv6flow' and ../afType!='l2vpnad' and ../afType!='mvpn' and ../afType!='evpn' and ../afType!='ipv4vpnmcast' and ../afType!='ls' and ../afType!='rpd' and ../afType!='mdt' and ../afType!='vpnv4flow' and ../afType!='vpnv6flow' and ../afType!='vpntarget' and ../afType!='mvpnv6'";
              type boolean;
              default "false";
              description
                "Packets are forwarded based on the next hop directly mapped to.
          label after label popping";
            }
            leaf preferenceExternal {
              when "not(../afType!='ipv4uni' and ../afType!='ipv4multi' and ../afType!='ipv6uni' or ../afType='ipv4labeluni' or ../afType='ipv4vpnmcast' or ../afType='mdt' or ../afType='rpd' or ../afType='vpntarget' or ../afType='vpnv4flow' or ../afType='vpnv6flow') or ../afType!='ipv6vpn' and ../afType!='ipv4vpn' and ../afType!='ipv4flow' and ../afType!='ipv6flow' and ../afType!='mvpn' and ../afType!='mvpnv6' and ../afType!='l2vpnad' and ../afType!='evpn' and ../afType!='ipv4vpnmcast' and ../afType!='mdt' and ../afType!='ls' and ../afType!='rpd' and ../afType!='ipv4labeluni' and not(../prefrencePolicyName)";
              type uint8 {
                range "1..255";
              }
              default "255";
              description
                "Set the protocol priority of EBGP routes. The value is an integer. An EBGP route is the optimal route learned from a peer outside the local AS.";
              ext:allowDelete "true";
            }
            leaf preferenceInternal {
              when "not(../afType!='ipv4uni' and ../afType!='ipv4multi' and ../afType!='ipv6uni' or ../afType='ipv4labeluni' or ../afType='ipv4vpnmcast' or ../afType='mdt' or ../afType='rpd' or ../afType='vpntarget' or ../afType='vpnv4flow' or ../afType='vpnv6flow') or ../afType!='ipv6vpn' and ../afType!='ipv4vpn' and ../afType!='ipv4flow' and ../afType!='ipv6flow' and ../afType!='mvpn' and ../afType!='mvpnv6' and ../afType!='l2vpnad' and ../afType!='evpn' and ../afType!='ipv4vpnmcast' and ../afType!='mdt' and ../afType!='ls' and ../afType!='rpd' and ../afType!='ipv4labeluni' and not(../prefrencePolicyName)";
              type uint8 {
                range "1..255";
              }
              default "255";
              description
                "Set the protocol priority of IBGP routes. The value is an integer. An IBGP route is a route learned from a peer inside the local AS.";
              ext:allowDelete "true";
            }
            leaf preferenceLocal {
              when "not(../afType!='ipv4uni' and ../afType!='ipv4multi' and ../afType!='ipv6uni' or ../afType='ipv4labeluni' or ../afType='ipv4vpnmcast' or ../afType='mdt' or ../afType='rpd' or ../afType='vpntarget' or ../afType='vpnv4flow' or ../afType='vpnv6flow') or ../afType!='ipv6vpn' and ../afType!='ipv4vpn' and ../afType!='ipv4flow' and ../afType!='ipv6flow' and ../afType!='mvpn' and ../afType!='mvpnv6' and ../afType!='l2vpnad' and ../afType!='evpn' and ../afType!='ipv4vpnmcast' and ../afType!='mdt' and ../afType!='ls' and ../afType!='rpd' and ../afType!='ipv4labeluni' and not(../prefrencePolicyName)";
              type uint8 {
                range "1..255";
              }
              default "255";
              description
                "Set the protocol priority of a local BGP route. The value is an integer. A local route refers to an automatically or manually summarized route.";
              ext:allowDelete "true";
            }
            leaf prefrencePolicyName {
              when "not(../afType!='ipv4uni' and ../afType!='ipv4multi' and ../afType!='ipv6uni' or ../afType!='ipv6vpn' and ../afType!='ipv4vpn' and ../afType!='ipv4flow' and ../afType!='ipv6flow' and ../afType!='mvpn' and ../afType!='mvpnv6' and ../afType!='l2vpnad' and ../afType!='evpn' and ../afType!='ipv4vpnmcast' and ../afType!='mdt' and ../afType!='ipv4labeluni' and ../afType!='ls' and ../afType!='rpd' or ../afType!='ipv6vpn' and ../afType!='ipv4vpn' and ../afType!='ipv4flow' and ../afType!='ipv6flow' and ../afType!='mvpn' and ../afType!='mvpnv6' and ../afType!='l2vpnad' and ../afType!='evpn' and ../afType!='ipv4vpnmcast' and ../afType!='mdt' and ../afType!='ls' and ../afType!='rpd' and ../afType!='vpntarget' or ../afType='ipv4labeluni' or ../afType='ipv4vpnmcast' or ../afType='mdt' or ../afType='rpd' or ../afType='vpntarget' or ../afType='vpnv4flow' or ../afType='vpnv6flow') or ../afType!='ipv6vpn' and ../afType!='ipv4vpn' and ../afType!='ipv4flow' and ../afType!='ipv6flow' and ../afType!='mvpn' and ../afType!='mvpnv6' and ../afType!='l2vpnad' and ../afType!='evpn' and ../afType!='ipv4vpnmcast' and ../afType!='mdt' and ../afType!='ls' and ../afType!='rpd' and ../afType!='ipv4labeluni' and ../preferenceExternal=255 and ../preferenceInternal=255 and ../preferenceLocal=255";
              type leafref {
                path "/rtp:rtp/rtp:routePolicys/rtp:routePolicy/rtp:name";
              }
              description
                "Set a routing policy to filter routes so that a configured priority is applied to the routes that match the specified policy. The routes that do not meet the policy rules use the default priority.";
              ext:allowDelete "true";
            }
            leaf qosId {
              when "not(../afType!='ipv4uni' and ../afType!='ipv6uni' and ../afType!='ipv4multi' and ../afType!='ls' and ../afType!='rpd' or ../afType='ipv4labeluni' or ../afType='ipv4vpnmcast' or ../afType='ls' or ../afType='mdt' or ../afType='rpd' or ../afType='vpntarget' or ../afType='vpnv4flow' or ../afType='vpnv6flow' or ../qosIdPolicyName and ../afType!='ipv4vpn' and ../afType!='ipv6vpn' and ../afType!='ipv4flow' and ../afType!='ipv6flow' and ../afType!='l2vpnad' and ../afType!='mvpn' and ../afType!='mvpnv6' and ../afType!='evpn' and ../afType!='ls' and ../afType!='rpd') or ../afType!='ipv4vpn' and ../afType!='ipv6vpn' and ../afType!='ipv4flow' and ../afType!='ipv6flow' and ../afType!='l2vpnad' and ../afType!='mvpn' and ../afType!='mvpnv6' and ../afType!='evpn' and ../afType!='ls' and ../afType!='rpd' and ../afType!='vpntarget' and ../afType!='ipv4labeluni' and not(../qosIdPolicyName)";
              type uint16 {
                range "1..255";
              }
              description
                "Specify the QoS local ID value";
              ext:allowDelete "true";
            }
            leaf qosIdPolicyName {
              when "not(../afType!='ipv4vpn' and ../afType!='ipv6vpn' and ../afType!='ipv4flow' and ../afType!='ipv6flow' and ../afType!='l2vpnad' and ../afType!='mvpn' and ../afType!='mvpnv6' and ../afType!='evpn' and ../afType!='ls' and ../afType!='rpd' and ../afType!='vpnv4flow' and ../afType!='vpnv6flow' and ../qosId!=65535 and ../qosId or ../afType='rpd' or ../afType='vpnv4flow' or ../afType='vpnv6flow') or ../afType!='ipv4vpn' and ../afType!='ipv6vpn' and ../afType!='ipv4flow' and ../afType!='ipv6flow' and ../afType!='l2vpnad' and ../afType!='mvpn' and ../afType!='mvpnv6' and ../afType!='evpn' and ../afType!='ls' and ../afType!='rpd' and ../afType!='vpntarget' and ../afType!='ipv4labeluni' and not(../qosId)";
              type leafref {
                path "/rtp:rtp/rtp:routePolicys/rtp:routePolicy/rtp:name";
              }
              description
                "Set a routing policy to filter routes so that a configured QoS ID is applied to the routes that match the specified policy. The routes that do not meet the policy rules use the default QoS ID.";
              ext:allowDelete "true";
            }
            leaf reflectBetweenClient {
              when "not(../afType='rpd') or ../afType='ls'";
              type boolean;
              default "true";
              description
                "Enable route reflection between clients. By default, route reflection is enabled between clients. If clients of a route reflector (RR) are fully meshed, you can disable route reflection among clients to reduce the cost.";
            }
            leaf reflectorClusterId {
              when "not(../afType='rpd') or ../afType='ls'";
              type uint32 {
                range "1..4294967295";
              }
              description
                "Set a cluster ID. Configuring multiple RRs in a cluster can enhance the stability of the network. If a cluster has more than one RR, select this option to set the same cluster ID for all the RRs to avoid routing loops. To allow clients to receive routes from RRs, ensure that the cluster ID of the RRs is different from the router ID of any client. If the cluster ID of the RRs is the same as the router ID of a client, the client will discard received routes.";
              ext:allowDelete "true";
            }
            leaf reflectorClusterIpv4 {
              when "not(../afType='rpd') or ../afType='ls'";
              type inet:ipv4-address-no-zone;
              description
                "Set a cluster ID. The value is expressed in the format of an IPv4 address. Configuring multiple RRs in a cluster can enhance the stability of the network. If a cluster has more than one RR, select this option to set the same cluster ID for all the RRs to avoid routing loops. To allow clients to receive routes from RRs, ensure that the cluster ID of the RRs is different from the router ID of any client. If the cluster ID of the RRs is the same as the router ID of a client, the client will discard received routes.";
              ext:allowDelete "true";
            }
            leaf rrFilterNumber {
              when "not(../../../vrfName!='_public_' or ../afType!='ipv4vpn' and ../afType!='ipv6vpn' and ../afType!='l2vpnad' and ../afType!='mvpn' and ../afType!='mdt' and ../afType!='mvpnv6' and ../afType!='evpn')";
              type leafref {
                path "/rtp:rtp/rtp:extendCommunityFilters/rtp:extendCommunityFilter/rtp:index";
              }
              description
                "Set the number of the extended community filter supported by an RR group. For the purpose of load balancing, only the IBGP route whose route-target extended community attribute meets the matching rules can be reflected. The name of an extended community filter can be a numeral or a character string. The ID of an extended community filter is an integer ranging from 1 to 399. The name of an extended community filter is a string of 1 to 51 characters. The string cannot contain only numerals.";
              ext:allowDelete "true";
            }
            leaf policyVpnTarget {
              when "not(../../../vrfName!='_public_' and ../afType='ipv4uni' or ../../../vrfName!='_public_' and ../afType='ipv6uni' or ../../../vrfName!='_public_' or ../afType!='ipv4vpn' and ../afType!='ipv6vpn' and ../afType!='l2vpnad' and ../afType!='mvpn' and ../afType!='mvpnv6' and ../../../vrfName='_public_' and ../afType!='mdt' and ../afType!='evpn' and ../afType!='vpnv4flow' and ../afType!='vpnv6flow' or ../afType='ipv4flow' or ../afType='ipv4labeluni' or ../afType='ipv6flow' or ../afType='ls') or ../../../vrfName='_public_' and ../afType='ipv4vpnmcast' or ../../../vrfName='_public_' and ../afType='mdt'";
              type boolean;
              default "false";
              description
                "Enable VPN target-based filtering for the received VPN routes. By default, VPN target-based filtering is enabled. Only the VPN route whose Export RT attribute matches the local Import RT attribute can be added to the routing table.  This option can be used in the inter-AS VPN Option B solution and the ASBR MP-EBGP inter-AS L2VPN solution in Kompella mode.";
            }
            leaf nextHopSelDependType {
              when "not(../../../vrfName!='_public_' or ../../../vrfName='_public_' and ../afType='ipv4multi' or ../../../vrfName='_public_' and ../afType='l2vpnad' or ../../../vrfName='_public_' and ../afType='mdt' or ../afType='evpn' or ../afType='ipv4flow' or ../afType='ipv6flow' or ../afType='l2vpnad' or ../afType='ls' or ../afType='mvpn' or ../afType='mvpnv6' or ../afType='rpd' or ../afType='vpntarget' or ../afType='vpnv4flow' or ../afType='vpnv6flow') or ../../../vrfName='_public_' and ../afType='ipv4labeluni' or ../../../vrfName='_public_' and ../afType='ipv4uni' or ../../../vrfName='_public_' and ../afType='ipv4vpn' or ../../../vrfName='_public_' and ../afType='ipv4vpnmcast' or ../../../vrfName='_public_' and ../afType='ipv6uni' or ../../../vrfName='_public_' and ../afType='ipv6vpn' or ../afType='evpn' and ../../../vrfName='_public_'";
              type bgpcommSelDependType;
              must "(../../../vrfName='_public_' and ../afType='ipv4labeluni' and (../nextHopSelDependType='dependTunnel' or ../nextHopSelDependType='dependIp') ) or (../../../vrfName='_public_' and ../afType='ipv4uni' and (../nextHopSelDependType='dependTunnel' or ../nextHopSelDependType='dependIp') ) or (../../../vrfName='_public_' and ../afType='ipv4vpn' and (../nextHopSelDependType='dependTunnel' or ../nextHopSelDependType='dependIp') ) or (../../../vrfName='_public_' and ../afType='ipv4vpnmcast' and (../nextHopSelDependType='dependTunnel' or ../nextHopSelDependType='dependIp') ) or (../../../vrfName='_public_' and ../afType='ipv6uni' and (../nextHopSelDependType='dependTunnel' or ../nextHopSelDependType='dependIp') ) or (../../../vrfName='_public_' and ../afType='ipv6vpn' and (../nextHopSelDependType='dependTunnel' or ../nextHopSelDependType='dependIp') ) or (../afType='evpn' and ../../../vrfName='_public_' and (../nextHopSelDependType='dependTunnel' or ../nextHopSelDependType='dependIp') ) or not(../../../vrfName='_public_' and ../afType='ipv4labeluni' or ../../../vrfName='_public_' and ../afType='ipv4uni' or ../../../vrfName='_public_' and ../afType='ipv4vpn' or ../../../vrfName='_public_' and ../afType='ipv4vpnmcast' or ../../../vrfName='_public_' and ../afType='ipv6uni' or ../../../vrfName='_public_' and ../afType='ipv6vpn' or ../afType='evpn' and ../../../vrfName='_public_')";
              default "dependIp";
              description
                "Specify the route iteration mode: IP or tunnel. In tunnel mode, the labeled BGP IPv4 route can participate in route selection only after its next hop is iterated to an LSP. In IP mode, the labeled BGP IPv4 route can participate in route selection only after its next hop is iterated to an IP address. By default, the labeled BGP IPv4 route can participate in route selection if its next hop can be iterated to an IP address, regardless of whether the LSP of the next hop exists. This allows the RR that is not enabled with MPLS to forward labeled routes. In non-RR networking or RR networking where the BGP next hop is changed, BGP needs to check whether there is an LSP destined for the next hop. If such an LSP is not found, BGP needs to establish an LSP in advance. If the default setting is adopted, a labeled BGP IPv4 unicast route may be selected prior to LSP establishment. As a result, services are incorrectly switched before LSP establishment and service stability is affected. Therefore, allow route selection only after the labeled BGP IPv4 route is iterated to an LSP.";
              ext:allowDelete "true";
            }
            leaf nextHopInheritIpcost {
              when "not(../afType='rpd' or ../afType='vpnv4flow' or ../afType='vpnv6flow') or ../../../vrfName='_public_' and ../nextHopSelDependType='dependTunnel'";
              type boolean;
              default "false";
              description
                "Specify the route iteration mode: IP or tunnel. In tunnel mode, the labeled BGP IPv4 route can participate in route selection only after its next hop is iterated to an LSP. ";
              ext:allowDelete "true";
            }
            leaf nhpRelayRoutePolicyName {
              when "not(../afType='evpn' or ../afType='ipv4flow' or ../afType='ipv4vpnmcast' or ../afType='ipv6flow' or ../afType='l2vpnad' or ../afType='ls' or ../afType='mdt' or ../afType='mvpn' or ../afType='mvpnv6' or ../afType='rpd' or ../afType='vpntarget' or ../afType='vpnv4flow' or ../afType='vpnv6flow') or ../afType!='ipv4flow' and ../afType!='ipv6flow' and ../afType!='l2vpnad' and ../afType!='mvpn' and ../afType!='mvpnv6' and ../afType!='evpn' and ../afType!='ipv4vpnmcast' and ../afType!='mdt' and ../afType!='ls' and ../afType!='rpd' and ../afType!='vpntarget'";
              type leafref {
                path "/rtp:rtp/rtp:routePolicys/rtp:routePolicy/rtp:name";
              }
              description
                "Specify the name of a route-policy for route iteration.";
              ext:allowDelete "true";
            }
            leaf explicitNull {
              when "not(../afType='ipv4vpnmcast' or ../afType='ls' or ../afType='mdt' or ../afType='rpd' or ../afType='vpntarget' or ../afType='vpnv4flow' or ../afType='vpnv6flow') or ../../../vrfName='_public_' and ../afType='ipv6uni'";
              type boolean;
              default "false";
              description
                "After 6PE routes are enabled to share a single label, all routes share the explicit-null label 2 when the 6PE sends IPv6 routes to its 6PE peer. This can save label resources on the 6PE. Therefore, when there are a large number of IPv6 routes that need to be sent, the problem that the IPv6 routes cannot be forwarded due to the shortage of labels can be avoided.";
            }
            leaf ebgpIfSensitive {
              when "not(../afType!='ipv4uni' and ../afType!='ipv4labeluni' and ../afType!='ipv6uni' or ../afType='ipv4vpnmcast' or ../afType='ls' or ../afType='mdt' or ../afType='rpd' or ../afType='vpntarget' or ../afType='vpnv4flow' or ../afType='vpnv6flow')";
              type boolean;
              default "true";
              description
                "After the function of EBGP interface fast sensing is enabled, the sessions of directly connected EBGP peers are immediately cleared from the associated interface when the interface becomes Down. By default, this function is enabled.";
            }
            leaf ibgpIfSensitive {
              when "not(../afType!='ipv4uni' and ../afType!='ipv6uni' or ../afType='ipv4vpnmcast' or ../afType='ls' or ../afType='mdt' or ../afType='rpd' or ../afType='vpntarget' or ../afType='vpnv4flow' or ../afType='vpnv6flow')";
              type boolean;
              default "false";
              description
                "After the function of IBGP interface fast sensing is enabled, the sessions of directly connected IBGP peers are immediately cleared from the associated interface when the interface becomes Down. By default, this function is disabled.";
            }
            leaf tunnelSelectorName {
              when "not(../afType='ipv4vpnmcast' or ../afType='ls' or ../afType='mdt' or ../afType='rpd' or ../afType='vpntarget' or ../afType='vpnv4flow' or ../afType='vpnv6flow') or ../afType!='ipv4multi' and ../afType!='ipv6uni' and ../afType!='ipv4flow' and ../afType!='ipv6flow' and ../afType!='l2vpnad' and ../../../vrfName='_public_' and ../afType!='mvpn' and ../afType!='mvpnv6' and ../afType!='evpn' and ../afType!='ls' and ../afType!='rpd' and ../afType!='vpntarget' and ../afType!='mdt' and ../afType!='ipv4vpnmcast'";
              type leafref {
                path "/rtp:rtp/rtp:tunnelSelectors/rtp:tunnelSelector/rtp:name";
              }
              description
                "Configure a tunnel selector and apply it to the BGP IPv4 unicast,BGP VPNv4 address families and BGP VPNv6 address families so that IPv4 ,VPNv4 and VPNv6 labeled routes can be iterated to tunnels based on the tunnel selector. By default, no tunnel selector is configured.";
              ext:allowDelete "true";
            }
            leaf tunnelSelectorAll {
              when "not(../afType='ipv4vpnmcast' or ../afType='mdt' or ../afType='rpd' or ../afType='vpntarget' or ../afType='vpnv4flow' or ../afType='vpnv6flow') or ../tunnelSelectorName and ../afType='ipv4uni'";
              type boolean;
              default "false";
              description
                "Tunnel selector for labeled, imported, and network segment routes.";
            }
            leaf reflectChgPath {
              when "not(../afType='evpn' or ../afType='ipv4flow' or ../afType='ipv6flow' or ../afType='ls' or ../afType='rpd' or ../afType='vpntarget' or ../afType='vpnv4flow' or ../afType='vpnv6flow') or ../afType!='ipv4flow' and ../afType!='ipv6flow' and ../afType!='ls' and ../afType!='rpd' and ../afType!='evpn'";
              type boolean;
              default "false";
              description
                "Enable an RR to use an export policy to change route AS_Path. By default, this function is not enabled.";
            }
            leaf bestExternal {
              when "not(../afType='ipv4vpnmcast' or ../afType='mdt' or ../afType='rpd' or ../afType='vpntarget' or ../afType='vpnv4flow' or ../afType='vpnv6flow') or ../../../vrfName='_public_' and ../afType!='ipv4multi' and ../afType!='ipv4flow' and ../afType!='ipv6flow' and ../afType!='l2vpnad' and ../afType!='mvpn' and ../afType!='mvpnv6' and ../afType!='evpn' and ../afType!='ls' and ../afType!='rpd' and ../afType!='vpntarget' and ../afType!='mdt' and ../afType!='ipv4vpnmcast'";
              type boolean;
              must "not(../determinMed='true') or (../determinMed='true' and ../bestExternal='false')";
              default "false";
              description
                "Enable Best External route selection.";
            }
            leaf slowPeerDet {
              when "not(../afType='rpd' or ../afType='vpnv4flow' or ../afType='vpnv6flow') or ../afType!='ipv4flow' and ../afType!='ipv6flow' and ../afType!='vpntarget'";
              type boolean;
              default "false";
              description
                "Detect slow peers";
            }
            leaf slowPeerThVal {
              when "not(../afType='rpd' or ../afType='vpnv4flow' or ../afType='vpnv6flow') or ../afType!='ipv4flow' and ../afType!='ipv6flow' and ../afType!='vpntarget'";
              type uint16 {
                range "120..3600";
              }
              default "300";
              description
                "Specify the time in seconds lagging behind average when a peer is determined to be a slow peer, default is 300";
              ext:allowDelete "true";
            }
            leaf slowPeerAbDet {
              when "not(../afType='rpd' or ../afType='vpnv4flow' or ../afType='vpnv6flow') or ../afType!='ipv4flow' and ../afType!='ipv6flow' and ../afType!='vpntarget'";
              type boolean;
              default "false";
              description
                "Enable absolute-detect slow peers.";
            }
            leaf slowPeerAbThVal {
              when "not(../afType='rpd' or ../afType='vpnv4flow' or ../afType='vpnv6flow') or ../afType!='ipv4flow' and ../afType!='ipv6flow' and ../afType!='vpntarget'";
              type uint16 {
                range "3..3600";
              }
              default "9";
              description
                "Specify the packet send delay time in second when a peer is determined to be a slow peer, default is 9";
              ext:allowDelete "true";
            }
            leaf addPathSelNum {
              when "not(../afType='ipv4vpnmcast' or ../afType='ls' or ../afType='mdt' or ../afType='rpd' or ../afType='vpntarget' or ../afType='vpnv4flow' or ../afType='vpnv6flow') or ../../../vrfName='_public_' and ../afType!='ipv4multi' and ../afType!='ipv4flow' and ../afType!='ipv6flow' and ../afType!='l2vpnad' and ../afType!='mvpn' and ../afType!='mvpnv6' and ../afType!='evpn' and ../afType!='ls' and ../afType!='rpd' and ../afType!='vpntarget' and ../afType!='mdt' and ../afType!='ipv4vpnmcast'";
              type uint8 {
                range "2..64";
              }
              must "not(../determinMed='true')";
              description
                "Number of Add-Path routes.";
              ext:allowDelete "true";
            }
            leaf enBestRtBitErrDetection {
              when "not(../afType='ipv4vpnmcast' or ../afType='mdt' or ../afType='rpd' or ../afType='vpntarget' or ../afType='vpnv4flow' or ../afType='vpnv6flow') or ../../../vrfName!='_public_' and ../afType!='ipv4flow' and ../afType!='ipv6flow' and ../afType!='ipv6uni'";
              type boolean;
              default "false";
              description
                "Enable the function to reroute traffic when a bit error event occurs.";
            }
            leaf bitErrDetectionEnable {
              when "not(../afType='ipv4vpnmcast' or ../afType='mdt' or ../afType='rpd' or ../afType='vpntarget' or ../afType='vpnv4flow' or ../afType='vpnv6flow') or ../afType='ipv4vpn'";
              type boolean;
              default "false";
              description
                "Enable association between bit error events and the adjustment of route attributes.";
            }
            leaf bitErrDetectionMed {
              when "not(../afType='ipv4vpnmcast' or ../afType='mdt' or ../afType='rpd' or ../afType='vpntarget' or ../afType='vpnv4flow' or ../afType='vpnv6flow') or ../afType='ipv4vpn' or ../bitErrDetectionEnable='true'";
              type uint32 {
                range "1..4294967295";
              }
              description
                "Specify the MED adjustment for BGP routes used when a bit error event occurs.";
              ext:allowDelete "true";
            }
            leaf bitErrDetectionLocalpref {
              when "not(../afType='ipv4vpnmcast' or ../afType='mdt' or ../afType='rpd' or ../afType='vpntarget' or ../afType='vpnv4flow' or ../afType='vpnv6flow') or ../afType='ipv4vpn' or ../bitErrDetectionEnable='true'";
              type uint32 {
                range "1..4294967295";
              }
              description
                "Specify the local preference adjustment for BGP routes used when a bit error event occurs.";
              ext:allowDelete "true";
            }
            leaf bitErrDetectionRtPolicy {
              when "not(../afType='ipv4vpnmcast' or ../afType='mdt' or ../afType='rpd' or ../afType='vpntarget' or ../afType='vpnv4flow' or ../afType='vpnv6flow') or ../afType='ipv4vpn' or ../bitErrDetectionEnable='true'";
              type leafref {
                path "/rtp:rtp/rtp:routePolicys/rtp:routePolicy/rtp:name";
              }
              description
                "Specify the name of a route-policy. The MED or local preference of only the routes that match the route-policy is adjusted.";
              ext:allowDelete "true";
            }
            leaf routeSelDelay {
              when "not(../afType='evpn' or ../afType='ipv4flow' or ../afType='ipv4vpnmcast' or ../afType='ipv6flow' or ../afType='ls' or ../afType='rpd' or ../afType='vpnv4flow' or ../afType='vpnv6flow') or ../afType!='mvpn' and ../afType!='mvpnv6' and ../afType!='evpn' and ../afType!='ipv4flow' and ../afType!='ipv6flow' and ../afType!='ls' and ../afType!='rpd' and ../afType!='ipv4vpnmcast' or ../afType='mvpn' and ../../../vrfName='_public_'";
              type uint16 {
                range "0..3600";
              }
              default "0";
              description
                "Route selection delay. ";
              ext:allowDelete "true";
            }
            leaf originAsValidEnable {
              when "not(../afType='ipv4vpnmcast' or ../afType='ls' or ../afType='mdt' or ../afType='rpd' or ../afType='vpntarget' or ../afType='vpnv4flow' or ../afType='vpnv6flow') or ../afType!='ipv4multi' and ../afType!='ipv4vpn' and ../afType!='ipv6vpn' and ../afType!='ipv4flow' and ../afType!='ipv6flow' and ../afType!='l2vpnad' and ../afType!='mvpn' and ../afType!='mvpnv6' and ../afType!='evpn' and ../afType!='ipv4vpnmcast' and ../afType!='mdt' and ../afType!='ls' and ../afType!='rpd' and ../afType!='vpntarget' and ../afType!='ipv4labeluni'";
              type boolean;
              default "false";
              description
                "Enable BGP origin AS validation.";
            }
            leaf originAsValid {
              when "not(../afType='ipv4labeluni' or ../afType='ipv4vpnmcast' or ../afType='ls' or ../afType='mdt' or ../afType='rpd' or ../afType='vpntarget' or ../afType='vpnv4flow' or ../afType='vpnv6flow') or ../afType!='ipv4multi' and ../afType!='ipv4vpn' and ../afType!='ipv6vpn' and ../afType!='ipv4flow' and ../afType!='ipv6flow' and ../afType!='l2vpnad' and ../afType!='mvpn' and ../afType!='mvpnv6' and ../afType!='evpn' and ../afType!='ipv4vpnmcast' and ../afType!='mdt' and ../afType!='ls' and ../afType!='rpd' and ../afType!='vpntarget' and ../afType!='ipv4labeluni' or ../originAsValidEnable='true'";
              type boolean;
              default "false";
              description
                "Apply the BGP origin AS validation result to route selection.";
            }
            leaf allowInvalidAs {
              when "not(../afType='ipv4vpnmcast' or ../afType='ls' or ../afType='mdt' or ../afType='rpd' or ../afType='vpntarget' or ../afType='vpnv4flow' or ../afType='vpnv6flow') or ../afType!='ipv4multi' and ../afType!='ipv4vpn' and ../afType!='ipv6vpn' and ../afType!='ipv4flow' and ../afType!='ipv6flow' and ../afType!='l2vpnad' and ../afType!='mvpn' and ../afType!='mvpnv6' and ../afType!='evpn' and ../afType!='ipv4vpnmcast' and ../afType!='mdt' and ../afType!='ls' and ../afType!='rpd' and ../afType!='vpntarget' and ../afType!='ipv4labeluni' or ../originAsValid='true'";
              type boolean;
              default "false";
              description
                "Allow routes with BGP origin AS validation result Invalid to be selected.";
            }
            leaf policyExtCommEnable {
              when "not(../afType='ipv4vpnmcast' or ../afType='ls' or ../afType='mdt' or ../afType='rpd' or ../afType='vpntarget' or ../afType='vpnv4flow' or ../afType='vpnv6flow') or ../afType!='ipv6vpn' and ../afType!='ipv4vpn' and ../afType!='ipv4flow' and ../afType!='ipv6flow' and ../afType!='mvpn' and ../afType!='mvpnv6' and ../afType!='l2vpnad' and ../afType!='evpn' and ../afType!='ipv4vpnmcast' and ../afType!='mdt' and ../afType!='ls' and ../afType!='rpd' and ../afType!='vpntarget'";
              type boolean;
              default "false";
              description
                "Change the extended community attribute.";
            }
            leaf policyQPPBEnable {
              when "not(../../../vrfName!='_public_' and ../afType='ipv4uni' or ../afType='ipv4flow' or ../afType='ipv4vpnmcast' or ../afType='ipv6flow' or ../afType='ls' or ../afType='mdt' or ../afType='rpd' or ../afType='vpntarget' or ../afType='vpnv4flow' or ../afType='vpnv6flow') or ../afType='ipv6uni'";
              type boolean;
              default "false";
              description
                "Enable QPPB.";
            }
            leaf supernetUniAdv {
              when "not(../afType='evpn' or ../afType='ipv4labeluni' or ../afType='ipv4vpnmcast' or ../afType='ls' or ../afType='mdt' or ../afType='mvpn' or ../afType='mvpnv6' or ../afType='rpd' or ../afType='vpntarget' or ../afType='vpnv4flow' or ../afType='vpnv6flow') or ../afType!='ipv4multi' and ../afType!='ipv4vpn' and ../afType!='ipv6vpn' and ../afType!='ipv4flow' and ../afType!='ipv6flow' and ../afType!='l2vpnad' and ../afType!='ls' and ../afType!='rpd' and ../afType!='vpntarget' and ../afType!='ipv4labeluni'";
              type boolean;
              default "false";
              description
                "Advertise supernet unicast routes.";
            }
            leaf supernetLabelAdv {
              when "not(../afType='rpd' or ../afType='vpnv4flow' or ../afType='vpnv6flow') or ../afType!='ipv4multi' and ../afType!='ipv4vpn' and ../afType!='ipv6uni' and ../afType!='ipv6vpn' and ../afType!='ipv4flow' and ../afType!='l2vpnad' and ../afType!='mvpn' and ../afType!='vpntarget' and ../afType!='evpn' and ../afType!='ipv4vpnmcast' and ../afType!='ls' and ../afType!='rpd' and ../afType!='mdt' and ../afType!='ipv6flow' and ../afType!='vpnv4flow' and ../afType!='vpnv6flow' and ../afType!='mvpnv6'";
              type boolean;
              default "true";
              description
                "Advertise supernet labeled routes.";
            }
            leaf ingressLspProtect {
              when "not(../afType='rpd') or ../../../vrfName='_public_' and ../afType!='ipv4multi' and ../afType!='ipv4vpn' and ../afType!='ipv6uni' and ../afType!='ipv6vpn' and ../afType!='ipv4flow' and ../afType!='l2vpnad' and ../afType!='mvpn' and ../afType!='vpntarget' and ../afType!='evpn' and ../afType!='ipv4vpnmcast' and ../afType!='ls' and ../afType!='rpd' and ../afType!='mdt' and ../afType!='ipv6flow' and ../afType!='vpnv4flow' and ../afType!='vpnv6flow' and ../afType!='mvpnv6'";
              type bgpcommIngressProtectModeType;
              default "null";
              description
                "Ingress LSP protection mode. By default, BGP FRR is not enabled.";
            }
            leaf ingressLspPolicyName {
              when "../../../vrfName='_public_' and (../afType='ipv4uni' or ../afType='ipv4labeluni')";
              type leafref {
                path "/rtp:rtp/rtp:routePolicys/rtp:routePolicy/rtp:name";
              }
              description
                "Name of a route-policy. An ingress LSP is created for only the routes that match the route-policy.";
              ext:allowDelete "true";
            }
            leaf applyLabelMode {
              when "not(../afType='ipv4vpnmcast' or ../afType='mdt' or ../afType='rpd' or ../afType='vpntarget' or ../afType='vpnv4flow' or ../afType='vpnv6flow') or ../afType!='ipv4uni' and ../afType!='ipv4labeluni' and ../afType!='ipv4multi' and ../afType!='ipv6uni' and ../afType!='ipv4flow' and ../afType!='ipv6flow' and ../afType!='l2vpnad' and ../afType!='mvpn' and ../afType!='mvpnv6' and ../afType!='ls' and ../afType!='rpd' and ../afType!='vpntarget'";
              type bgpcommApplyLabelType;
              default "perRoute";
              description
                "Method of distributing labels to VPNV4 and VPNV6 routes. The way which assigns the label depends on the paf value. If there are a large number of routes, assign a label for the routes that have same nexthop and out-label. This allows all routes which have same nexthop and out-label to use one label.";
              ext:allowDelete "true";
            }
            leaf labelAdvEnable {
              when "not(../afType='ipv4vpnmcast' or ../afType='mdt' or ../afType='rpd' or ../afType='vpntarget' or ../afType='vpnv4flow' or ../afType='vpnv6flow') or ../../../vrfName='_public_' and ../afType='ipv4uni'";
              type boolean;
              default "false";
              description
                "Unicast-route advertise label.";
            }
            leaf originatorPrior {
              when "not(../afType='ipv4vpnmcast' or ../afType='ls' or ../afType='mdt' or ../afType='rpd' or ../afType='vpnv4flow' or ../afType='vpnv6flow') or ../afType!='ipv4flow' and ../afType!='ipv6flow' and ../afType!='mvpn' and ../afType!='mvpnv6' and ../afType!='evpn' and ../afType!='ipv4vpnmcast' and ../afType!='mdt' and ../afType!='ls' and ../afType!='rpd'";
              type boolean;
              default "false";
              description
                "Configure BGP to compare originator before clusterlist in route selection.";
            }
            leaf lowestPriority {
              when "not(../afType='ipv4vpnmcast' or ../afType='mdt' or ../afType='rpd' or ../afType='vpnv4flow' or ../afType='vpnv6flow') or ../../../vrfName='_public_' and ../afType!='ipv4multi' and ../afType!='ipv4vpn' and ../afType!='ipv6vpn' and ../afType!='ipv4vpnmcast' and ../afType!='mdt' and ../afType!='ls' and ../afType!='rpd' and ../afType!='evpn' and ../afType!='vpntarget'";
              type boolean;
              default "false";
              description
                "Reduce route priority to lowest.";
            }
            leaf relayDelayEnable {
              when "not(../afType!='ipv4uni' and ../afType!='ipv4labeluni' and ../afType!='ipv6uni' and ../afType!='ipv4vpn' and ../afType!='ipv6vpn' or ../afType='rpd' or ../afType='vpnv4flow' or ../afType='vpnv6flow')";
              type boolean;
              default "true";
              description
                "Enable relay delay processing.";
              ext:allowDelete "true";
            }
            leaf uniRtRelayTnl {
              when "not(../../../vrfName!='_public_' and ../afType='ipv4flow' or ../../../vrfName!='_public_' and ../afType='ipv6flow' or ../afType='ipv4flow' or ../afType='ipv4labeluni' or ../afType='ipv6flow' or ../afType='mvpn' or ../afType='mvpnv6' or ../afType='rpd' or ../afType='vpntarget' or ../afType='vpnv4flow' or ../afType='vpnv6flow') or ../afType!='ipv4multi' and ../afType!='ipv4vpn' and ../afType!='ipv6vpn' and ../afType!='ipv4flow' and ../afType!='ipv6flow' and ../afType!='l2vpnad' and ../afType!='mvpn' and ../afType!='mvpnv6' and ../afType!='evpn' and ../afType!='ls' and ../afType!='rpd' and ../afType!='ipv4vpnmcast' and ../afType!='mdt' and ../afType!='vpntarget'";
              type boolean;
              default "false";
              description
                "Unicast-route recursive-lookup tunnel.";
            }
            leaf uniRtTnlSelName {
              when "not(../../../vrfName!='_public_' and ../afType='ipv4flow' or ../../../vrfName!='_public_' and ../afType='ipv6flow' or ../afType='ipv4flow' or ../afType='ipv4labeluni' or ../afType='ipv6flow' or ../afType='mvpn' or ../afType='mvpnv6' or ../afType='rpd' or ../afType='vpntarget' or ../afType='vpnv4flow' or ../afType='vpnv6flow') or ../uniRtRelayTnl='true'";
              type leafref {
                path "/rtp:rtp/rtp:tunnelSelectors/rtp:tunnelSelector/rtp:name";
              }
              description
                "Unicast-route tunnel selector name.";
              ext:allowDelete "true";
            }
            leaf vrfImportnhpinvariable {
              when "not(../afType='ipv4vpnmcast' or ../afType='mdt' or ../afType='rpd' or ../afType='vpntarget' or ../afType='vpnv4flow' or ../afType='vpnv6flow') or ../../../vrfName!='_public_' and ../afType!='ipv4flow' and ../afType!='ipv6flow'";
              type boolean;
              default "false";
              description
                "Configure the command to enable advertise the route without modifying the next-hop.";
            }
            leaf redirectIpRelayTnlEnable {
              when "../../../vrfName='_public_' and ../afType='ipv4flow'";
              type boolean;
              default "false";
              description
                "Flow-route Recursive-lookup Tunnel";
              ext:allowDelete "true";
            }
            leaf redirectIpRelayTnlSelName {
              when "../../../vrfName='_public_' and ../afType='ipv4flow' or ../redirectIpRelayTnlEnable='true'";
              type leafref {
                path "/rtp:rtp/rtp:tunnelSelectors/rtp:tunnelSelector/rtp:name";
              }
              description
                "Flow-route Tunnel Selector Name";
              ext:allowDelete "true";
            }
            leaf lspMtu {
              when "../../../vrfName='_public_' and ../afType!='ipv4flow' and ../afType!='ipv6flow' and ../afType!='l2vpnad' and ../afType!='mvpn' and ../afType!='mvpnv6' and ../afType!='evpn' and ../afType!='ipv4vpnmcast' and ../afType!='mdt' and ../afType!='ls' and ../afType!='rpd' and ../afType!='vpntarget' and ../afType!='vpnv6flow'";
              type uint16 {
                range "46..65535";
              }
              default "1500";
              description
                "BGP LSP MTU";
              ext:allowDelete "true";
            }
            leaf timerForEor {
              when "not(../afType!='vpntarget' or ../afType='rpd' or ../afType='vpnv4flow' or ../afType='vpnv6flow')";
              type uint32 {
                range "3..3000";
              }
              default "180";
              description
                "Time waiting for the End-Of-RIB.";
              ext:allowDelete "true";
            }
            leaf externalPathNum {
              when "not(../afType!='vpntarget' or ../afType='ipv4labeluni' or ../afType='rpd' or ../afType='vpnv4flow' or ../afType='vpnv6flow')";
              type uint16 {
                range "0..64";
              }
              default "0";
              description
                "The number of external path";
              ext:allowDelete "true";
            }
            leaf rtFilterDisable {
              when "not(../afType!='vpntarget' or ../afType='rpd' or ../afType='vpnv4flow' or ../afType='vpnv6flow')";
              type boolean;
              default "false";
              description
                "The flag whether Route Target routing-table filer ability is enabled ";
              ext:allowDelete "true";
            }
            leaf nexthopDelayTime {
              when "not(../afType!='ipv4vpn' and ../afType!='ipv6vpn' and ../afType!='ipv4uni' and ../afType!='ipv4labeluni' and ../afType!='ipv4multi' and ../afType!='ipv6uni' and ../afType!='evpn' or ../afType='ipv4labeluni')";
              type uint32 {
                range "1..100";
              }
              description
                "Configure the delay-time of nexthop.";
              ext:allowDelete "true";
            }
            leaf noCriticalNexthopDelayTime {
              when "not(../afType!='ipv4vpn' and ../afType!='ipv6vpn' and ../afType!='ipv4uni' and ../afType!='ipv4labeluni' and ../afType!='ipv4multi' and ../afType!='ipv6uni' and ../afType!='evpn' or ../afType='ipv4labeluni')";
              type uint32 {
                range "1..100";
              }
              description
                "Configure the no-critical delay-time of nexthop.";
              ext:allowDelete "true";
            }
            leaf flowValidationModeAs  {
              when "not(../afType='rpd' or ../afType='vpnv4flow' or ../afType='vpnv6flow') or ../afType='ipv4flow' or ../afType='ipv6flow'";
              type boolean;
              default "false";
              description
                "Using the route validation-mode include-as command, you can configure flow-route validation mode include as.";
            }
            leaf ingressLspLoadBalancNum {
              when "../../../vrfName='_public_' and (../afType='ipv4uni' or ../afType='ipv4labeluni')";
              type uint16 {
                range "1..65535";
              }
              default "1";
              description
                "Maximum number of ingress LSPs for load balancing. The default value is 1, indicating that this attribute is not configured. Configuring the number of ingress LSPs for load balancing and configuring BGP FRR of ingress LSPs are mutually exclusive.";
            }
            leaf transitLspLoadBalancNum {
              when "../../../vrfName='_public_' and (../afType='ipv4uni' or ../afType='ipv4labeluni')";
              type uint16 {
                range "1..65535";
              }
              default "1";
              description
                "Maximum number of transit LSPs for load balancing. The default value is 1, indicating that this attribute is not configured.";
            }
            leaf aigp {
              when "not(../afType!='ipv6uni' and ../../../vrfName!='_public_' and ../afType!='ipv4uni')";
              type boolean;
              default "false";
              description
                "Enable route with AIGP attribute for route selection.";
            }
            leaf locatorName {
              when "../../../vrfName!='_public_' and ../afType!='ipv6uni' and ../afType!='ipv4flow' and ../afType!='ipv6flow'";
              type leafref {
                path "/segripv6:segripv6/segripv6:srv6Locators/segripv6:srv6Locator/segripv6:locatorName";
              }
              description
                "Locator for BGP Import. The name is a string of case-sensitive characters.";
              ext:allowDelete "true";
            }
            leaf autoSid {
              when "../../../vrfName!='_public_' and ../afType!='ipv6uni' and ../afType!='ipv4flow' and ../afType!='ipv6flow' and ../afType!='ipv4labeluni'";
              type boolean;
              default "false";
              description
                "SID automatic allocation ability.";
            }
            leaf srIpv6Mode {
              when "../../../vrfName!='_public_' and ../afType!='ipv6uni' and ../afType!='ipv4flow' and ../afType!='ipv6flow' and ../afType!='ipv4labeluni'";
              type bgpcommSrv6Mode;
              default "null";
              description
                "Srv6 Tunnel Iteration Mode.";
            }
            leaf routerIdFilter {
              when "../afType='rpd'";
              type boolean;
              default "false";
              description
                "Enables router ID filtering.";
            }
            leaf rpdPolicyChangeDelay {
              when "../../../vrfName='_public_' and ../afType='ipv4uni'";
              type uint16 {
                range "0..180";
              }
              default "30";
              description
                "Delay for the response to RPD policy changes. The value is in seconds, and the default value is 30.";
            }
            leaf vpnOrfEnable {
              when "not(../afType!='mvpn' and ../afType!='l2vpnad')";
              type boolean;
              default "false";
              description
                "Enable vpn-orf capability.";
            }
            leaf advRouteMode {
              when "../../../vrfName!='_public_' and ../afType!='ipv4multi' and ../afType!='ipv4vpn' and ../afType!='ipv6vpn' and ../afType!='ipv4flow' and ../afType!='ipv6flow' and ../afType!='l2vpnad' and ../afType!='mvpn' and ../afType!='evpn' and ../afType!='ipv4vpnmcast' and ../afType!='mdt' and ../afType!='ls' and ../afType!='vpntarget' and ../afType!='vpnv4flow' and ../afType!='ipv4labeluni' and ../afType!='mvpnv6' and ../afType!='rpd'";
              type bgpcommAdvRouteMode;
              default "all";
              description
                "VPN advertise routes according to type.";
            }
            leaf attrSetEnable {
              when "not(../../../vrfName='_public_') and (../afType='ipv4uni' or ../afType='ipv6uni')";
              type boolean;
              default "false";
              description
                "Enable the capability of processing attribute set.";
            }
            leaf attrSetMode {
              when "../attrSetEnable='true'";
              type bgpcommAttrSetType;
              default "both";
              description
                "The processing mode of attribute set.";
            }
            leaf bestrouteMedConfederation {
              when "not(../../../vrfName!='_public_' or ../afType!='ipv4uni' and ../afType!='ipv6uni' and ../afType!='ipv4labeluni' and ../afType!='ipv4multi' and ../../../vrfName='_public_')";
              type boolean;
              default "false";
              description
                "Configure BGP to compare Med value only within the federation.";
            }
            container evpnBgpAFConfig {
              description
                "Configuration of the EVPN address family.";
              leaf dfDelayTime {
                when "../../afType='evpn'";
                type uint32 {
                  range "0..1200";
                }
                default "60";
                description
                  "Delay for DF election.";
                ext:allowDelete "true";
              }
            }
            container vrfAFBriefInfo {
              config false;
              description
                "Address family information.";
              leaf peerNum {
                type uint32;
                config false;
                description
                  "Set the number of peers in a specified address family.";
              }
              leaf routeNum {
                type uint32;
                config false;
                description
                  "Set the number of routes in a specified address family.";
              }
              leaf rdNum {
                type uint32;
                config false;
                description
                  "Number of RDs.";
              }
            }
            container peerGroupAFs {
              description
                "List of all peer groups that are enabled in a specified address family.";
              list peerGroupAF {
                when "not(../../afType='ipv4flow' or ../../afType='ipv6flow' or ../../afType='rpd' or ../../afType='vpnv4flow' or ../../afType='vpnv6flow') or ../../afType!='ipv4flow' and ../../afType!='ipv6flow' and ../../afType!='vpnv4flow' and ../../afType!='vpnv6flow' and ../../afType!='rpd'";
                key "groupName";
                description
                  "Peer group enabled in a specified address family.";
                leaf groupName {
                  type leafref {
                    path "../../../../../bgpPeerGroups/bgpPeerGroup/groupName";
                  }
                  description
                    "Configure a name for a peer group. The value is a string, spaces not supported.";
                }
                leaf groupType {
                  type bgpcommPeerType;
                  mandatory true;
                  description
                    "Configure a peer group type: IBGP or EBGP. The type must be consistent with the peer group type.";
                }
                leaf advertiseRemoteNexthop {
                  when "not(../../../afType='ipv4vpnmcast' or ../../../afType='mdt' or ../../../afType='vpntarget') or ../../../afType='ipv4vpn'";
                  type boolean;
                  default "false";
                  description
                    "Advertise the remote nexthop to a peer or a peer group. By default, the remote nexthop attribute is not advertised to any peer.";
                }
                leaf advertiseCommunity {
                  when "../../../afType!='ipv4vpnmcast' and ../../../afType!='ls' or ../../../afType!='ls'";
                  type boolean;
                  default "false";
                  description
                    "Advertise the community attribute to a peer or a peer group. By default, the community attribute is not advertised to any peer.";
                }
                leaf advertiseExtCommunity {
                  when "not(../../../afType='evpn' or ../../../afType='ipv4vpnmcast' or ../../../afType='mdt' or ../../../afType='mvpn' or ../../../afType='mvpnv6' or ../../../afType='vpntarget') or ../../../afType!='ipv6vpn' and ../../../afType!='ipv4vpn' and ../../../afType!='l2vpnad' and ../../../afType!='evpn' and ../../../afType!='ipv4vpnmcast' and ../../../afType!='ls' and ../../../afType!='vpntarget'";
                  type boolean;
                  default "false";
                  description
                    "Advertise the extended community attribute to a peer or a peer group. By default, the extended community attribute is not advertised to any peer.";
                }
                leaf discardExtCommunity {
                  when "not(../../../afType='ipv4vpnmcast' or ../../../afType='mdt' or ../../../afType='vpntarget') or ../../../afType!='ipv4vpn' and ../../../afType!='ipv6vpn' and ../../../afType!='l2vpnad' and ../../../afType!='mvpn' and ../../../afType!='mvpnv6' and ../../../afType!='evpn' and ../../../afType!='ipv4vpnmcast' and ../../../afType!='mdt' and ../../../afType!='ls' and ../../../afType!='vpntarget' or ../../../afType!='ipv6vpn' and ../../../afType!='ipv4vpn' and ../../../afType!='l2vpnad' and ../../../afType!='evpn' and ../../../afType!='ipv4vpnmcast' and ../../../afType!='ls' and ../../../afType!='vpntarget'";
                  type boolean;
                  default "false";
                  description
                    "Discard the extended community attribute in the routes learned from a specified peer. By default, the extended community attribute is not discarded. ";
                }
                leaf allowAsLoopEnable {
                  when "not(../../../afType='ipv4vpnmcast' or ../../../afType='mdt' or ../../../afType='mvpn' or ../../../afType='mvpnv6') or ../../../afType!='ipv4flow' and ../../../afType!='ipv6flow' and ../../../afType!='mvpn' and ../../../afType!='mvpnv6' and ../../../afType!='ipv4vpnmcast' and ../../../afType!='mdt' and ../../../afType!='ls' and ../../../afType!='evpn'";
                  type boolean;
                  default "false";
                  description
                    "Allow the repetitive local AS numbers. By default, local AS numbers cannot be repeated.";
                }
                leaf allowAsLoopLimit {
                  when "not(../../../afType='ipv4vpnmcast' or ../../../afType='mdt') or ../../../afType!='ipv4flow' and ../../../afType!='ipv6flow' and ../../../afType!='mvpn' and ../../../afType!='mvpnv6' and ../../../afType!='ipv4vpnmcast' and ../../../afType!='mdt' and ../../../afType!='ls' and ../../../afType!='evpn' or ../allowAsLoopEnable='true'";
                  type uint32 {
                    range "1..10";
                  }
                  description
                    "Configure the number of allowed AS number repetition times. The value is an integer. The default value is 1.";
                  ext:allowDelete "true";
                }
                leaf keepAllRoutes {
                  when "not(../../../afType='evpn' or ../../../afType='ipv4labeluni' or ../../../afType='ipv4vpnmcast' or ../../../afType='mdt' or ../../../afType='mvpn' or ../../../afType='mvpnv6' or ../../../afType='vpntarget') or ../../../afType!='ipv4flow' and ../../../afType!='ipv6flow' and ../../../afType!='l2vpnad' and ../../../afType!='mvpn' and ../../../afType!='mvpnv6' and ../../../afType!='evpn' and ../../../afType!='ipv4vpnmcast' and ../../../afType!='mdt' and ../../../afType!='ls' and ../../../afType!='vpntarget' and ../../../afType!='ipv4labeluni'";
                  type boolean;
                  default "false";
                  description
                    "Save all the updated information about BGP routes from a specified peer or peer group after a BGP connection is established, even though these BGP routes fail to match the routing policy on the ingress. By default, the updated information about BGP routes from a specified peer is saved only when the routes match the routing policy on the ingress. If a router supports route refreshing, this option is not required.";
                }
                leaf nextHopConfigure {
                  when "not(../../../afType!='ipv4uni' and ../../../afType!='ipv4labeluni' and ../../../afType!='ipv6uni' and ../../../afType!='ipv4vpn' and ../../../afType!='ipv6vpn' and ../../../afType!='evpn' and ../../../afType!='l2vpnad' and ../../../afType!='mvpn' and ../../../afType!='mvpnv6' and ../../../afType!='mdt' and ../../../afType!='ipv4multi' or ../../../afType='ipv4vpnmcast')";
                  type bgpcommNextHopCfg;
                  must "(../../../afType!='ipv4uni' and ../../../afType!='ipv4labeluni' and ../../../afType!='ipv4vpn' and ../../../afType!='ipv6vpn' and ../../../afType!='l2vpnad' and ../../../afType!='evpn' and (../nextHopConfigure='null' or ../nextHopConfigure='local') ) or ((not(../../../afType!='ipv4uni' and ../../../afType!='ipv4labeluni' and ../../../afType!='ipv4vpn' and ../../../afType!='ipv6vpn' and ../../../afType!='l2vpnad' and ../../../afType!='evpn') and (../nextHopConfigure='null' or ../nextHopConfigure='local' or ../nextHopConfigure='invariable') ))";
                  default "null";
                  description
                    "Both the next-hop-local mode and next-hop-invariable mode are available when the peer address family is the VPNv4/VPNV6/L2VPN AD address family. Only the next-hop-local mode is available when the peer address family is not VPNv4/VPNV6/L2VPN AD address family. In next-hop-local mode, you can configure a BGP speaker to set its IP address of as the next hop of the routes to be advertised to IBGP peers or IBGP peer groups. In next-hop-invariable mode, you can configure PEs in different ASs not to change the next hop of routes when the PEs advertise the routes to their EBGP peers and use the next hop addresses of IGP routes to advertise imported IGP routes to IBGP peers. By default, when a BGP speaker advertises routes to EBGP peers and imported IGP routes to IBGP peers, the BGP speaker changes the next hop to its interface address. ";
                  ext:allowDelete "true";
                }
                leaf preferredValue {
                  when "not(../../../afType='evpn' or ../../../afType='ipv4vpnmcast' or ../../../afType='mdt' or ../../../afType='mvpn' or ../../../afType='mvpnv6') or ../../../afType!='ipv6vpn' and ../../../afType!='ipv4vpnmcast' and ../../../afType!='mdt' and ../../../afType!='ls'";
                  type uint32 {
                    range "0..65535";
                  }
                  default "0";
                  description
                    "Assign a preferred value for the routes learned from a specified peer. The value is an integer. By default, the preferred value of the route learnt from BGP peers is 0. After a preferred value is configured for the routes learned from a specified peer, all the routes that learnt from this peer will use this preferred value. When multiple routes reach the same address prefix, the route with the largest preferred value will be selected.";
                  ext:allowDelete "true";
                }
                leaf loadBalancingEnable {
                  when "not(../../../afType='ipv4vpnmcast' or ../../../afType='mdt' or ../../../afType='vpntarget') or ../../../afType!='mvpn' and ../../../afType!='mvpnv6' and ../../../afType!='evpn' and ../../../afType!='ipv4vpnmcast' and ../../../afType!='mdt' and ../../../afType!='ipv4vpn' and ../../../afType!='ipv6vpn' and ../../../afType!='l2vpnad' and ../../../afType!='ipv4flow' and ../../../afType!='ipv6flow' and ../../../afType!='ls' and ../../../afType!='vpntarget'";
                  type boolean;
                  default "false";
                  description
                    "Enable a neighbour to participate in load balancing.";
                }
                leaf loadBalancingIgnoreAs {
                  when "not(../../../afType='ipv4vpnmcast' or ../../../afType='mdt' or ../../../afType='vpntarget') or ../../../afType!='mvpn' and ../../../afType!='mvpnv6' and ../../../afType!='evpn' and ../../../afType!='ipv4vpnmcast' and ../../../afType!='mdt' and ../../../afType!='ipv4vpn' and ../../../afType!='ipv6vpn' and ../../../afType!='l2vpnad' and ../../../afType!='ipv4flow' and ../../../afType!='ipv6flow' and ../../../afType!='ls' and ../../../afType!='vpntarget' or ../loadBalancingEnable='true'";
                  type boolean;
                  default "false";
                  description
                    "Configure BGP to ignore the AS_Path attribute when selecting the equal route. By default, BGP uses the AS_Path attribute as one of route selection rules. After as-path-neglect is selected, BGP does not compare the AS_Path length.";
                }
                leaf loadBalancingRelaxAs {
                  when "not(../../../afType='ipv4vpnmcast' or ../../../afType='mdt' or ../../../afType='vpntarget') or ../../../afType!='mvpn' and ../../../afType!='mvpnv6' and ../../../afType!='evpn' and ../../../afType!='ipv4vpnmcast' and ../../../afType!='mdt' and ../../../afType!='ipv4vpn' and ../../../afType!='ipv6vpn' and ../../../afType!='l2vpnad' and ../../../afType!='ipv4flow' and ../../../afType!='ipv6flow' and ../../../afType!='ls' and ../../../afType!='vpntarget' or ../loadBalancingEnable='true'";
                  type boolean;
                  default "false";
                  description
                    "Configure BGP to ignore comparison of AS_Path attributes with the same length when selecting the equal route. By default, BGP uses the AS_Path attribute as one of route selection rules. After as-path-neglect is selected, BGP does not compare the AS_Path length.";
                }
                leaf publicAsOnly {
                  when "not(../../../afType='ipv4vpnmcast' or ../../../afType='mdt') or ../../../afType!='ipv4flow' and ../../../afType!='ipv6flow' and ../../../afType!='mvpn' and ../../../afType!='mvpnv6' and ../../../afType!='ipv4vpnmcast' and ../../../afType!='mdt' and ../../../afType!='ls' and ../../../afType!='evpn'";
                  type boolean;
                  default "false";
                  description
                    "Configure BGP to send Update packets carrying only public AS numbers. By default, private AS numbers can be carried in BGP Update packets.";
                }
                leaf publicAsOnlyForce {
                  when "../publicAsOnly='true' and ../publicAsOnlyLimited='false'";
                  type boolean;
                  must "(../../../afType!='mvpn' and ../../../afType!='mvpnv6' and ../../../afType!='ipv4flow' and ../../../afType!='ipv6flow' and ../../../afType!='evpn' and ../publicAsOnly='false' and ../../../afType!='ipv4vpnmcast' and ../../../afType!='mdt' and ../../../afType!='ls' and ../publicAsOnlyForce='false') or (../publicAsOnlyLimited='true' and ../publicAsOnlyForce='false') or not(../../../afType!='mvpn' and ../../../afType!='mvpnv6' and ../../../afType!='ipv4flow' and ../../../afType!='ipv6flow' and ../../../afType!='evpn' and ../publicAsOnly='false' and ../../../afType!='ipv4vpnmcast' and ../../../afType!='mdt' and ../../../afType!='ls' or ../publicAsOnlyLimited='true')";
                  default "false";
                  description
                    "Configures BGP to carry only the public AS number instead of the private AS number when BGP sends Update packets. By default, BGP can carry the private AS number when BGP sends Update packets.";
                  ext:allowDelete "true";
                }
                leaf publicAsOnlyLimited {
                  when "../publicAsOnly='true' and ../publicAsOnlyForce='false'";
                  type boolean;
                  must "(../../../afType!='mvpn' and ../../../afType!='mvpnv6' and ../../../afType!='ipv4flow' and ../../../afType!='ipv6flow' and ../../../afType!='evpn' and ../publicAsOnly='false' and ../../../afType!='ipv4vpnmcast' and ../../../afType!='mdt' and ../../../afType!='ls' and ../publicAsOnlyLimited='false') or (../publicAsOnlyForce='true' and ../publicAsOnlyLimited='false') or not(../../../afType!='mvpn' and ../../../afType!='mvpnv6' and ../../../afType!='ipv4flow' and ../../../afType!='ipv6flow' and ../../../afType!='evpn' and ../publicAsOnly='false' and ../../../afType!='ipv4vpnmcast' and ../../../afType!='mdt' and ../../../afType!='ls' or ../publicAsOnly='true' and ../publicAsOnlyForce='false' or ../publicAsOnlyForce='true')";
                  default "false";
                  description
                    "When the BGP sends update packets, the left ends of both the local AS and public AS do not carry the private AS. By default, BGP can carry the private AS number when BGP sends Update packets.";
                  ext:allowDelete "true";
                }
                leaf publicAsOnlyReplace {
                  when "../../../afType!='mvpn' and ../../../afType!='mvpnv6' and ../../../afType!='ipv4flow' and ../../../afType!='ipv6flow' and ../../../afType!='evpn' and ../publicAsOnly='true' and ../../../afType!='ipv4vpnmcast' and ../../../afType!='mdt' and ../../../afType!='ls'";
                  type boolean;
                  must "not(../../../afType!='mvpn' and ../../../afType!='mvpnv6' and ../../../afType!='ipv4flow' and ../../../afType!='ipv6flow' and ../../../afType!='evpn' and ../publicAsOnly='false' and ../../../afType!='ipv4vpnmcast' and ../../../afType!='mdt' and ../../../afType!='ls') or (../../../afType!='mvpn' and ../../../afType!='mvpnv6' and ../../../afType!='ipv4flow' and ../../../afType!='ipv6flow' and ../../../afType!='evpn' and ../publicAsOnly='false' and ../../../afType!='ipv4vpnmcast' and ../../../afType!='mdt' and ../../../afType!='ls' and ../publicAsOnlyReplace='false')";
                  default "false";
                  description
                    "When the BGP sends update packets, the private AS is replaced by the local AS. By default, BGP can carry the private AS number when BGP sends Update packets.";
                  ext:allowDelete "true";
                }
                leaf publicAsOnlySkipPeerAs {
                  when "../../../afType!='mvpn' and ../../../afType!='mvpnv6' and ../../../afType!='ipv4flow' and ../../../afType!='ipv6flow' and ../../../afType!='evpn' and ../publicAsOnly='true' and ../../../afType!='ipv4vpnmcast' and ../../../afType!='mdt' and ../../../afType!='ls'";
                  type boolean;
                  must "not(../../../afType!='mvpn' and ../../../afType!='mvpnv6' and ../../../afType!='ipv4flow' and ../../../afType!='ipv6flow' and ../../../afType!='evpn' and ../publicAsOnly='false' and ../../../afType!='ipv4vpnmcast' and ../../../afType!='mdt' and ../../../afType!='ls') or (../../../afType!='mvpn' and ../../../afType!='mvpnv6' and ../../../afType!='ipv4flow' and ../../../afType!='ipv6flow' and ../../../afType!='evpn' and ../publicAsOnly='false' and ../../../afType!='ipv4vpnmcast' and ../../../afType!='mdt' and ../../../afType!='ls' and ../publicAsOnlySkipPeerAs='false')";
                  default "false";
                  description
                    "When the BGP sends update packets, the neigbour AS is not processed. By default, BGP can carry the private AS number when BGP sends Update packets.";
                  ext:allowDelete "true";
                }
                leaf routeLimit {
                  type uint32 {
                    range "1..4294967295";
                  }
                  description
                    "Configure the maximum number of routes that can be accepted from a peer. ";
                  ext:allowDelete "true";
                }
                leaf acceptPrefixEnable {
                  when "not(../../../afType='mvpn' or ../../../afType='mvpnv6') or ../../../afType!='mvpn' and ../../../afType!='mvpnv6' and ../routeLimit";
                  type boolean;
                  default "false";
                  description
                    "Enable the device to keep receiving routes and the routes are valid if the maximum number of routes allowed have been received and the alert-only parameter is specified.";
                  ext:allowDelete "true";
                }
                leaf routeLimitPercent {
                  when "../routeLimit";
                  type uint8 {
                    range "1..100";
                  }
                  default "75";
                  description
                    "Specify the percentage of routes when a router starts to generate an alarm. The default value is 75.";
                  ext:allowDelete "true";
                }
                leaf routeLimitType {
                  when "../routeLimit";
                  type bgpcommRouteLmtType;
                  default "noparameter";
                  description
                    "Set the processing method as alert-only, idle-forever, or idle-timeout when the number of routes exceeds the set threshold. When alert-only is used, only an alarm is generated when the number of routes exceeds the threshold. In this case, new routes are no longer accepted. When idle-forever is used, connections are not automatically reestablished after being cut off until BGP connections are reset if the number of routes exceeds the set threshold. When idle-timeout is used and the idle-timeout timer is specified, the connections are automatically reestablished after being cut off if the number of routes exceeds the set threshold. You can reset BGP connections to reestablish the connections before the idle-timeout times expires.";
                  ext:allowDelete "true";
                }
                leaf routeLimitIdleTimeout {
                  when "../routeLimitType='idleTimeout'";
                  type uint16 {
                    range "1..1200";
                  }
                  default "1";
                  description
                    "Specify the value of the idle-timeout timer to automatically reestablish the connections after they are cut off when the number of routes exceeds the set threshold.";
                  ext:allowDelete "true";
                }
                leaf rtUpdtInterval {
                  when "../../../afType!='evpn'";
                  type uint16 {
                    range "0..600";
                  }
                  description
                    "Specify the minimum interval at which Update packets are sent. The value is an integer, in seconds. By default, the interval at which Update packets are sent to IBGP peers is 15s, and the interval at which Update packets are sent to EBGP peers is 30s. When routes change, a router will send Update packets to notify its peers. If a route changes frequently, you can set an interval at which Update packets are sent to prevent the router from sending Update packets each time the route changes. This configuration is valid only to the routes learned from peers. ";
                  ext:allowDelete "true";
                }
                leaf reflectClient {
                  when "../../../../../vrfName='_public_' and (../../../afType='ipv4uni' or ../../../afType='ipv4vpn' or ../../../afType='ipv6uni' or ../../../afType='ipv6vpn' or ../../../afType='ipv4labeluni')";
                  type boolean;
                  default "false";
                  description
                    "Configure the local device as a route reflector (RR) and a peer or peer group as its client. By default, the RR and its client are not configured. This configuration is applicable between IBGP peers only. The configurations of RRs and its clients in an address family are valid only in this address family. Therefore, it is recommended to configure RRs and its clients in the specified address family that is required.";
                }
                leaf substituteAsEnable {
                  when "../../../afType!='ipv4multi' and ../../../afType!='ipv4vpn' and ../../../afType!='ipv6vpn' and ../../../afType!='ipv4flow' and ../../../afType!='ipv6flow' and ../../../afType!='l2vpnad' and ../../../afType!='mvpn' and ../../../afType!='mvpnv6' and ../../../afType!='evpn' and ../../../afType!='ipv4vpnmcast' and ../../../afType!='mdt' and ../../../afType!='ls' and ../../../afType!='vpntarget'";
                  type boolean;
                  default "false";
                  description
                    "Replace the AS number of a specified peer in the AS_Path attribute with the local AS number. By default, the AS number replacement is disabled. On a PE where AS number replacement is enabled, if an AS number in the AS_Path attribute of a route is same as that of the CE to which the PE advertises the route, the PE replaces the AS number with its own AS number before advertising the route.";
                }
                leaf importRtPolicyName {
                  when "../../../afType!='rpd'";
                  type leafref {
                    path "/rtp:rtp/rtp:routePolicys/rtp:routePolicy/rtp:name";
                  }
                  description
                    "Specify the filtering policy applied to the routes learned from a peer. By default, no such policy is specified.";
                  ext:allowDelete "true";
                }
                leaf exportRtPolicyName {
                  when "../../../afType!='rpd'";
                  type leafref {
                    path "/rtp:rtp/rtp:routePolicys/rtp:routePolicy/rtp:name";
                  }
                  description
                    "Specify the filtering policy applied to the routes to be advertised to a peer. By default, no such policy is specified.";
                  ext:allowDelete "true";
                }
                leaf ignoreBitError {
                  when "not(../../../afType='ipv4vpnmcast' or ../../../afType='mdt' or ../../../afType='vpntarget') or not(../exportRtPolicyName) and ../../../afType='ipv4vpn'";
                  type boolean;
                  default "false";
                  description
                    "Configure the peer to ignore bit error detection results when applying a route-policy.";
                  ext:allowDelete "true";
                }
                leaf importPrefFiltName {
                  when "not(../../../afType!='ipv4uni' and ../../../afType!='ipv4labeluni' and ../../../afType!='ipv4multi' and ../../../afType!='ipv4vpn' and ../../../afType!='mdt' or ../../../afType='evpn' or ../../../afType='ipv4vpnmcast' or ../../../afType='mvpn' or ../../../afType='mvpnv6') or ../../../afType='mdt'";
                  type leafref {
                    path "/rtp:rtp/rtp:prefixFilters/rtp:prefixFilter/rtp:name";
                  }
                  must "not(../../../afType='vpntarget')";
                  description
                    "Specify the IPv4 filtering policy applied to the routes received from a specified peer. By default, no such policy is specified.";
                  ext:allowDelete "true";
                }
                leaf importPref6FiltName {
                  when "not(../../../afType!='ipv6uni' and ../../../afType!='ipv6vpn' or ../../../afType='ipv4vpnmcast' or ../../../afType='mdt' or ../../../afType='vpntarget')";
                  type leafref {
                    path "/rtp:rtp/rtp:ipv6PrefixFilters/rtp:ipv6PrefixFilter/rtp:name";
                  }
                  description
                    "Specify the IPv6 filtering policy applied to the routes received from a specified peer. By default, no such policy is specified.";
                  ext:allowDelete "true";
                }
                leaf exportPrefFiltName {
                  when "not(../../../afType!='ipv4uni' and ../../../afType!='ipv4labeluni' and ../../../afType!='ipv4multi' and ../../../afType!='ipv4vpn' and ../../../afType!='mdt' or ../../../afType='evpn' or ../../../afType='ipv4vpnmcast' or ../../../afType='mdt' or ../../../afType='mvpn' or ../../../afType='mvpnv6' or ../../../afType='vpntarget')";
                  type leafref {
                    path "/rtp:rtp/rtp:prefixFilters/rtp:prefixFilter/rtp:name";
                  }
                  description
                    "Specify the IPv4 filtering policy applied to the routes to be advertised to a specified peer. By default, no such policy is specified.";
                  ext:allowDelete "true";
                }
                leaf exportPref6FiltName {
                  when "not(../../../afType!='ipv6uni' and ../../../afType!='ipv6vpn' or ../../../afType='ipv4vpnmcast' or ../../../afType='mdt' or ../../../afType='vpntarget')";
                  type leafref {
                    path "/rtp:rtp/rtp:ipv6PrefixFilters/rtp:ipv6PrefixFilter/rtp:name";
                  }
                  description
                    "Specify the IPv6 filtering policy applied to the routes to be advertised to a specified peer. By default, no such policy is specified.";
                  ext:allowDelete "true";
                }
                leaf importAsPathNameOrNum {
                  when "not(../../../afType='ipv4vpnmcast' or ../../../afType='mdt' or ../../../afType='vpntarget') or ../../../afType!='ipv4flow' and ../../../afType!='ipv6flow' and ../../../afType!='l2vpnad' and ../../../afType!='evpn' and ../../../afType!='ipv4vpnmcast' and ../../../afType!='ls' and ../../../afType!='vpntarget'";
                  type leafref {
                    path "/rtp:rtp/rtp:asPathFilters/rtp:asPathFilter/rtp:index";
                  }
                  description
                    "Apply an AS_Path-based filtering policy to the routes received from a specified peer. The policy can be identified with a name or number, and the number ranges from 1 to 256. By default, no such policy is specified. Therefore, all BGP routes can be accepted.";
                  ext:allowDelete "true";
                }
                leaf exportAsPathNameOrNum {
                  when "not(../../../afType='ipv4vpnmcast' or ../../../afType='mdt' or ../../../afType='vpntarget') or ../../../afType!='ipv4flow' and ../../../afType!='ipv6flow' and ../../../afType!='l2vpnad' and ../../../afType!='evpn' and ../../../afType!='ipv4vpnmcast' and ../../../afType!='ls' and ../../../afType!='vpntarget'";
                  type leafref {
                    path "/rtp:rtp/rtp:asPathFilters/rtp:asPathFilter/rtp:index";
                  }
                  description
                    "Apply an AS_Path-based filtering policy to the routes to be advertised to a specified peer. The policy can be identified with a name or number, and the number ranges from 1 to 256. By default, no such policy is specified. Therefore, all BGP routes can be advertised.";
                  ext:allowDelete "true";
                }
                leaf importAclNameOrNum {
                  when "not(../../../afType!='ipv4uni' and ../../../afType!='ipv4labeluni' and ../../../afType!='ipv4multi' and ../../../afType!='ipv4vpn' and ../../../afType!='mdt' or ../../../afType='ipv4vpnmcast' or ../../../afType='vpntarget') or ../../../afType='mdt'";
                  type leafref {
                    path "/acl:acl/acl:aclGroups/acl:aclGroup/acl:aclNumOrName";
                  }
                  description
                    "Apply an IPv4 ACL-based filtering policy to the routes received from a specified peer. The ACL number ranges from 2000 to 2999, and the name must start with a letter. By default, no such policy is specified. Therefore, all BGP routes can be accepted.";
                  ext:allowDelete "true";
                }
                leaf importAcl6NameOrNum {
                  when "not(../../../afType!='ipv6uni' and ../../../afType!='ipv6vpn' or ../../../afType='ipv4vpnmcast' or ../../../afType='mdt' or ../../../afType='vpntarget')";
                  type leafref {
                    path "/acl:acl/acl:aclGroup6s/acl:aclGroup6/acl:aclNumOrName";
                  }
                  description
                    "Apply an IPv6 ACL-based filtering policy to the routes received from a specified peer. The ACL number ranges from 2000 to 2999, and the name must start with a letter. By default, no such policy is specified. Therefore, all BGP routes can be accepted.";
                  ext:allowDelete "true";
                }
                leaf exportAclNameOrNum {
                  when "not(../../../afType!='ipv4uni' and ../../../afType!='ipv4labeluni' and ../../../afType!='ipv4multi' and ../../../afType!='ipv4vpn' and ../../../afType!='mdt' or ../../../afType='ipv4vpnmcast' or ../../../afType='mdt' or ../../../afType='vpntarget')";
                  type leafref {
                    path "/acl:acl/acl:aclGroups/acl:aclGroup/acl:aclNumOrName";
                  }
                  description
                    "Apply an IPv4 ACL-based filtering policy to the routes to be advertised to a specified peer. The ACL number ranges from 2000 to 2999, and the name must start with a letter. By default, no such policy is specified. Therefore, all BGP routes can be advertised.";
                  ext:allowDelete "true";
                }
                leaf exportAcl6NameOrNum {
                  when "not(../../../afType!='ipv6uni' and ../../../afType!='ipv6vpn' or ../../../afType='ipv4vpnmcast' or ../../../afType='mdt' or ../../../afType='vpntarget')";
                  type leafref {
                    path "/acl:acl/acl:aclGroup6s/acl:aclGroup6/acl:aclNumOrName";
                  }
                  description
                    "Apply an IPv6 ACL-based filtering policy to the routes to be advertised to a specified peer. The ACL number ranges from 2000 to 2999, and the name must start with a letter. By default, no such policy is specified. Therefore, all BGP routes can be advertised.";
                  ext:allowDelete "true";
                }
                leaf ipprefixOrfEnable {
                  when "../../../../../vrfName='_public_' and ../../../afType='ipv4uni'";
                  type boolean;
                  must "not(../isNonstdIpprefixMod='true' and ../ipprefixOrfEnable='true')";
                  default "false";
                  description
                    "Enable Prefix-based BGP outbound route filtering (ORF). By default, this function is not enabled. ORF enables a BGP device to use the import policy of a peer as the local export policy so that unwanted routes are filtered out during route advertisement.";
                  ext:allowDelete "true";
                }
                leaf isNonstdIpprefixMod {
                  when "../../../../../vrfName='_public_' and ../../../afType='ipv4uni'";
                  type boolean;
                  must "not(../isNonstdIpprefixMod='true' and ../ipprefixOrfEnable='true')";
                  default "false";
                  description
                    "Enable Huawei routers to be compatible with Nonstandard routers. The ORF capability codes supported by Nonstandard devices are different from that defined by the associated RFC standard. After the option is selected, Huawei devices and Nonstandard devices negotiate ORF capability based on the ORF capability code supported by Nonstandard devices. If the option is not selected, Huawei devices and Nonstandard devices negotiate ORF capability based on the ORF capability code specified by the RFC standard.";
                  ext:allowDelete "true";
                }
                leaf orftype {
                  when "not(../../../afType='ipv4labeluni' or ../../../afType='ipv4vpnmcast' or ../../../afType='mdt' or ../../../afType='vpntarget') or ../../../afType='ipv4uni'";
                  type uint16;
                  default "0";
                  description
                    "ORF Type.";
                }
                leaf orfMode {
                  when "../../../../../vrfName='_public_' and ../../../afType='ipv4uni'";
                  type bgpcommonOrfMode;
                  must "(../ipprefixOrfEnable!='true' and ../isNonstdIpprefixMod!='true' and (../orfMode='null') ) or ((not(../ipprefixOrfEnable!='true' and ../isNonstdIpprefixMod!='true') and (../orfMode='receive' or ../orfMode='send' or ../orfMode='both') ))";
                  default "null";
                  description
                    "Configure an outbound route filtering (ORF) mode, which can be Receive, Send, or Both, and the default ORF mode is Both. ";
                  ext:allowDelete "true";
                }
                leaf soostring {
                  when "not(../../../afType='ipv4vpnmcast' or ../../../afType='mdt' or ../../../afType='vpntarget') or ../../../../../vrfName!='_public_' or ../../../afType!='ipv4multi' and ../../../afType!='ipv4vpn' and ../../../afType!='ipv6vpn' and ../../../afType!='ipv4flow' and ../../../afType!='ipv6flow' and ../../../afType!='l2vpnad' and ../../../afType!='mvpn' and ../../../afType!='mvpnv6' and ../../../afType!='evpn' and ../../../afType!='ipv4vpnmcast' and ../../../afType!='mdt' and ../../../afType!='ls' or ../../../afType!='ipv4multi' and ../../../afType!='ipv4vpn' and ../../../afType!='ipv6vpn' and ../../../afType!='ipv4flow' and ../../../afType!='ipv6flow' and ../../../afType!='l2vpnad' and ../../../afType!='mvpn' and ../../../afType!='mvpnv6' and ../../../afType!='evpn' and ../../../afType!='mdt' and ../../../afType!='ls' and ../../../afType!='vpntarget' and ../../../../../vrfName!='_public_' or ../../../afType='ipv4uni' and ../../../../../vrfName!='_public_' or ../../../afType='ipv6uni' and ../../../../../vrfName!='_public_'";
                  type string {
                    length "3..21";
                  }
                  description
                    "Configure the Site-of-Origin (SoO) extended community attribute. This attribute can be expressed in the following formats: X.X.X.X:number<0-65535>, number<0-65535>:number<0-4294967295>, or number<0-65535>.number<0-65535>:number<0-65535>  or <65536-4294967295>:<0-65535>. 0:0 or 0.0:0 is not supported. 
Two CEs are in the same site and can advertise routes to each other, and they are connected to a VPN through PEs. If the local routes of a CE are advertised to the other CE over the VPN, a routing loop may occur. 
The SoO feature can prevent a route advertised by a site from being sent back to the site, preventing routing loops. After SoO is enabled and a PE receives a route from a CE, the specified SoO attribute will be added to the route. Before advertising the route to the other CE, the PE checks the SoO attribute. If the SoO attribute is the same as the locally configured SoO attribute, the PE does not advertise the route, preventing routing loops. ";
                  ext:allowDelete "true";
                }
                leaf defaultRtAdvEnable {
                  when "not(../../../afType!='ipv4uni' and ../../../afType!='ipv4multi' and ../../../afType!='ipv6uni' and ../../../afType!='vpntarget' or ../../../afType='ipv4labeluni' or ../../../afType='ipv4vpnmcast' or ../../../afType='mdt')";
                  type boolean;
                  default "false";
                  description
                    "Enable a device to advertise the default route to its peers. By default, the device does not advertise the default route to any peer or peer group. This option enables a device to send a default route with the device as the next hop address to its peers, regardless of whether there is a default route in the local routing table.";
                }
                leaf defaultRtAdvPolicy {
                  when "not(../../../afType!='ipv4uni' and ../../../afType!='ipv4multi' and ../../../afType!='ipv6uni' and ../../../afType!='vpntarget' or ../../../afType!='ipv4vpn' and ../../../afType!='ipv6vpn' and ../../../afType!='ipv4flow' and ../../../afType!='ipv6flow' and ../../../afType!='l2vpnad' and ../../../afType!='mvpn' and ../../../afType!='mvpnv6' and ../../../afType!='evpn' and ../../../afType!='ipv4vpnmcast' and ../../../afType!='mdt' and ../../../afType!='ls' and ../../../afType!='ipv4labeluni' and ../defaultRtAdvEnable='false' or ../../../afType='ipv4labeluni' or ../../../afType='ipv4vpnmcast' or ../../../afType='mdt' or ../../../afType='vpntarget') or ../../../afType!='ipv4vpn' and ../../../afType!='ipv6vpn' and ../../../afType!='ipv4flow' and ../../../afType!='ipv6flow' and ../../../afType!='l2vpnad' and ../../../afType!='mvpn' and ../../../afType!='mvpnv6' and ../../../afType!='evpn' and ../../../afType!='ipv4vpnmcast' and ../../../afType!='mdt' and ../../../afType!='ls' and ../../../afType!='vpntarget' and ../../../afType!='ipv4labeluni' and ../defaultRtAdvEnable='true'";
                  type leafref {
                    path "/rtp:rtp/rtp:routePolicys/rtp:routePolicy/rtp:name";
                  }
                  description
                    "Specify the name of a used policy. The value is a string.";
                  ext:allowDelete "true";
                }
                leaf defaultRtMatchMode {
                  when "not(../../../afType='ipv4labeluni' or ../../../afType='ipv4vpnmcast' or ../../../afType='mdt' or ../../../afType='vpntarget') or ../../../afType!='ipv4vpn' and ../../../afType!='ipv6vpn' and ../../../afType!='l2vpnad' and ../../../afType!='mvpn' and ../../../afType!='mvpnv6' and ../../../afType!='mdt' and ../../../afType!='evpn' and ../../../afType!='ipv4flow' and ../../../afType!='ipv6flow' and ../../../afType!='ipv4vpnmcast' and ../../../afType!='ls' and ../../../afType!='vpntarget' and ../../../afType!='ipv4labeluni' and ../defaultRtAdvEnable='true'";
                  type bgpcommonCraMatchMode;
                  default "null";
                  description
                    "Configure the matching mode of default route advertisement, which can be disabling of route advertisement conditions, enabling of all route advertisement conditions, and enabling of part route advertisement conditions. Enabling of all route advertisement conditions indicates that a default route can be advertised only when it matches all the conditions. Enabling of part route advertisement conditions indicates that a default route can be advertised only when it matches one condition.";
                  ext:allowDelete "true";
                }
                leaf labelRouteCapability {
                  when "../../../afType!='ipv4multi' and ../../../afType!='ipv4vpn' and ../../../afType!='ipv6vpn' and ../../../afType!='ipv4flow' and ../../../afType!='ipv6flow' and ../../../afType!='l2vpnad' and ../../../afType!='mvpn' and ../../../afType!='evpn' and ../../../afType!='ls' and ../../../afType!='ipv4vpnmcast' and ../../../afType!='vpntarget' and ../../../afType!='mvpnv6' and ../../../afType!='ipv6uni' and ../../../afType!='mdt' and ../../../afType!='vpnv4flow' and ../../../afType!='vpnv6flow' and ../../../afType!='ipv4labeluni' and ../../../afType!='rpd'";
                  type boolean;
                  default "false";
                  description
                    "Enable a device to exchange labeled routes";
                  ext:allowDelete "true";
                }
                leaf checkTunnelReachable {
                  when "not(../../../afType='ipv4vpnmcast' or ../../../afType='mdt' or ../../../afType='vpntarget')";
                  type boolean;
                  default "false";
                  description
                    "Enable tunnel reachability check.";
                  ext:allowDelete "true";
                }
                leaf checkWithdrawType {
                  when "not(../../../afType='ipv4labeluni' or ../../../afType='ipv4vpnmcast' or ../../../afType='mdt')";
                  type boolean;
                  default "false";
                  description
                    "Enable withdraw type check.";
                  ext:allowDelete "true";
                }
                leaf upeEnable {
                  when "not(../../../afType='ipv4vpnmcast' or ../../../afType='mdt' or ../../../afType='vpntarget') or ../../../afType='ipv4vpn'";
                  type boolean;
                  default "false";
                  description
                    "Configure the peer as an underlayer PE (UPE). ";
                  ext:allowDelete "true";
                }
                leaf advBestExternal {
                  when "../../../../../vrfName='_public_' and (../../../afType='ipv4uni' or ../../../afType='ipv4vpn' or ../../../afType='ipv6uni' or ../../../afType='ipv6vpn' or ../../../afType='ipv4labeluni')";
                  type boolean;
                  must "not(../reflectClient='true' and ../advBestExternal='true')";
                  must "not((../addPathMode and ../addPathMode!='null') and ../advBestExternal='true')";
                  must "not(../advAddPathNum and ../advBestExternal='true')";
                  default "false";
                  description
                    "Enable the device to advertise Best External routes to peers.";
                }
                leaf addPathMode {
                  when "../../../../../vrfName='_public_' and (../../../afType='ipv4uni' or ../../../afType='ipv4vpn' or ../../../afType='ipv6uni' or ../../../afType='ipv6vpn' or ../../../afType='ipv4labeluni')";
                  type bgpcommAddPathCapType;
                  default "null";
                  description
                    "Enable Add-Path route advertisement to a peer group.";
                  ext:allowDelete "true";
                }
                leaf advAddPathNum {
                  when "../../../../../vrfName='_public_' and (../../../afType='ipv4uni' or ../../../afType='ipv4vpn' or ../../../afType='ipv6uni' or ../../../afType='ipv6vpn' or ../../../afType='ipv4labeluni')";
                  type uint8 {
                    range "2..64";
                  }
                  description
                    "Number of Add-Path routes that can be advertised to a peer group.";
                  ext:allowDelete "true";
                }
                leaf originAsValid {
                  when "not(../../../afType='evpn' or ../../../afType='ipv4flow' or ../../../afType='ipv4labeluni' or ../../../afType='ipv4multi' or ../../../afType='ipv4vpnmcast' or ../../../afType='ipv6flow' or ../../../afType='l2vpnad' or ../../../afType='ls' or ../../../afType='mdt' or ../../../afType='mvpn' or ../../../afType='mvpnv6' or ../../../afType='vpntarget' or ../advertiseExtCommunity='false' and ../../../afType='ipv4uni' or ../advertiseExtCommunity='false' and ../../../afType='ipv6uni') or ../advertiseExtCommunity='true' and ../../../afType!='ipv4multi' and ../../../afType!='ipv4flow' and ../../../afType!='ipv6flow' and ../../../afType!='l2vpnad' and ../../../afType!='mvpn' and ../../../afType!='mvpnv6' and ../../../afType!='evpn' and ../../../afType!='ipv4vpnmcast' and ../../../afType!='mdt' and ../../../afType!='ls' and ../../../afType!='vpntarget' and ../../../afType!='ipv4labeluni' or ../advertiseExtCommunity='true' and ../../../afType='ipv6uni'";
                  type boolean;
                  default "false";
                  description
                    "Advertises the BGP origin AS validation result to the specified BGP peer or peer group.";
                  ext:allowDelete "true";
                }
                leaf expMode {
                  when "not(../../../afType='evpn' or ../../../afType='ipv4labeluni' or ../../../afType='ipv4vpnmcast' or ../../../afType='mdt' or ../../../afType='mvpn' or ../../../afType='mvpnv6' or ../../../afType='vpntarget') or ../../../afType!='ipv4multi' and ../../../afType!='ipv4vpn' and ../../../afType!='ipv6vpn' and ../../../afType!='ipv4flow' and ../../../afType!='ipv6flow' and ../../../afType!='l2vpnad' and ../../../afType!='ipv4flow' and ../../../afType!='ipv6flow' and ../../../afType!='evpn' and ../../../afType!='mdt' and ../../../afType!='ls' and ../../../afType!='vpntarget'";
                  type bgpcommExpModeType;
                  default "null";
                  description
                    "Specify the ASs in which a BGP label can inherit the QoS priority carried in the outer label of public tunnel in the Core AS and the ASs in which the priorities of BGP LSPs must be restored before the LSPs are advertised to a non-core AS.";
                  ext:allowDelete "true";
                }
                leaf vplsEnable {
                  when "not(../../../afType!='l2vpnad' or ../../../afType='ipv4vpnmcast' or ../../../afType='mdt' or ../../../afType='vpntarget')";
                  type boolean;
                  default "false";
                  description
                    "Enable Virtual Private LAN Services";
                  ext:allowDelete "true";
                }
                leaf vplsAdDisable {
                  when "not(../../../afType!='l2vpnad' or ../../../afType='ipv4vpnmcast' or ../../../afType='mdt' or ../../../afType='vpntarget')";
                  type boolean;
                  default "false";
                  description
                    "Enable Virtual private LAN service auto-discovery.Not receive BGP-AD Route.";
                  ext:allowDelete "true";
                }
                leaf vpwsEnable {
                  when "not(../../../afType!='l2vpnad')";
                  type boolean;
                  default "false";
                  description
                    "Enable Virtual Private Wire Services";
                  ext:allowDelete "true";
                }
                leaf updatePktStandardCompatible {
                  when "../../../afType='ipv4vpnmcast'";
                  type boolean;
                  default "false";
                  description
                    "Compatible Standard update packet";
                  ext:allowDelete "true";
                }
                leaf advertiseIrb {
                  when "../../../afType='evpn'";
                  type boolean;
                  default "false";
                  description
                    "Adervertise IRB Route when its value is true.  The default value is false.";
                }
                leaf advertiseArp {
                  when "../../../afType='evpn'";
                  type boolean;
                  default "false";
                  description
                    "Adervertise ARP Route when its value is true.  The default value is false.";
                }
                leaf advertiseIrbv6 {
                  when "../../../afType='evpn'";
                  type boolean;
                  default "false";
                  description
                    "Adervertise IRBv6 Route when its value is true.  The default value is false.";
                }
                leaf advertiseND {
                  when "../../../afType='evpn'";
                  type boolean;
                  default "false";
                  description
                    "Adervertise ND Route when its value is true.  The default value is false.";
                }                
                leaf aigp {
                  when "not(../../../../../vrfName!='_public_' or ../../../afType!='ipv4uni' and ../../../afType!='ipv4vpn' and ../../../afType!='ipv6uni' and ../../../afType!='ipv6vpn' and ../../../afType!='ipv4labeluni')";
                  type boolean;
                  default "false";
                  description
                    "Enable route with AIGP attribute advertisement to or from a peer.";
                  ext:allowDelete "true";
                }
                leaf advertiseEncapType {
                  when "../../../afType='evpn'";
                  type advertiseEncapType;
                  default "mpls";
                  description
                    "Encapsulation type of packets.";
                  ext:allowDelete "true";
                }
                leaf reoriginatedRtEnable {
                  when "not(../../../../../vrfName!='_public_' and ../../../afType='ipv4flow' or ../../../../../vrfName!='_public_' and ../../../afType='ipv6flow') or ../../../../../vrfName='_public_' and ../../../afType!='ipv4flow' and ../../../afType!='ipv6flow' and ../../../afType!='ipv4multi' and ../../../afType!='ipv4uni' and ../../../afType!='ipv4labeluni' and ../../../afType!='ipv6uni' and ../../../afType!='ipv6vpn' and ../../../afType!='l2vpnad' and ../../../afType!='mvpn' and ../../../afType!='ipv4vpnmcast' and ../../../afType!='mdt' and ../../../afType!='ls' and ../../../afType!='vpntarget'";
                  type boolean;
                  default "false";
                  description
                    "Enable route regeneration.";
                }
                leaf macIpRtEnable {
                  when "not(../../../../../vrfName!='_public_' and ../../../afType='ipv4flow' or ../../../../../vrfName!='_public_' and ../../../afType='ipv6flow') or ../../../../../vrfName='_public_' and ../../../afType!='ipv4flow' and ../../../afType!='ipv6flow' and ../../../afType!='ipv4multi' and ../../../afType!='ipv4uni' and ../../../afType!='ipv4labeluni' and ../../../afType!='ipv6uni' and ../../../afType!='ipv6vpn' and ../../../afType!='l2vpnad' and ../../../afType!='mvpn' and ../../../afType!='ipv4vpnmcast' and ../../../afType!='mdt' and ../../../afType!='ls' and ../../../afType!='vpntarget'";
                  type boolean;
                  default "false";
                  description
                    "Enable MAC-IP route regeneration and advertisement.";
                }
                leaf macRtEnable {
                  when "../../../afType='evpn'";
                  type boolean;
                  default "false";
                  description
                    "Enable MAC route regeneration and advertisement.";
                }
                leaf ipRtEnable {
                  when "../../../afType='ipv4vpn'";
                  type boolean;
                  default "false";
                  description
                    "Enable IP route regeneration and advertisement.";
                }
                leaf vpnv4RtEnable {
                  when "../../../afType='evpn'";
                  type boolean;
                  default "false";
                  description
                    "Enable VPNv4 route regeneration and advertisement.";
                }
                leaf reoriginatedRtEnableDc {
                  when "../../../afType='evpn'";
                  type boolean;
                  default "false";
                  description
                    "Enable route regeneration.";
                }
                leaf macIpRtEnableDc {
                  when "../../../afType='evpn'";
                  type boolean;
                  default "false";
                  description
                    "Enable MAC-IP route regeneration and advertisement.";
                }
                leaf ipRtEnableDc {
                  when "../../../afType='evpn'";
                  type boolean;
                  default "false";
                  description
                    "Enable IP route regeneration and advertisement.";
                }
                leaf allowClusterCap {
                  when "../../../afType='vpntarget'";
                  type boolean;
                  default "false";
                  description
                    "allowClusterCap";
                  ext:allowDelete "true";
                }
                leaf allowClusterNum {
                  when "../../../afType='vpntarget' or ../allowClusterCap='true'";
                  type uint8 {
                    range "1..10";
                  }
                  description
                    "allowClusterNum";
                  ext:allowDelete "true";
                }
                leaf advCmulMatNhp {
                  when "not(../../../afType!='mvpn' and ../../../afType!='mvpnv6')";
                  type boolean;
                  default "false";
                  description
                    "enable advertise C-multicast route directional, only advertise to the neighbor which is matched the nexthop in intra-AD route.";
                  ext:allowDelete "true";
                }
                leaf esadCompatible {
                  when "../../../afType='evpn'";
                  type boolean;
                  default "false";
                  description
                    "Ethernet A-D per ES Route Compatible.";
                  ext:allowDelete "true";
                }
                leaf splitGroupName {
                  when "../../../afType='evpn'";
                  type string {
                    length "1..31";
                  }
                  description
                    "Split group name.";
                  ext:allowDelete "true";
                }
                leaf nhpStaticRtEnable {
                  when "../../../afType='ipv4uni'";
                  type boolean;
                  must "../nextHopConfigure='invariable' or (not(../nextHopConfigure='invariable') and ../nhpStaticRtEnable='false')";
                  default "false";
                  description
                    "Static route enable for next-hop-invariable.";
                  ext:allowDelete "true";
                }
				leaf upgCfgIndependent  {
                  when "../../../afType!='rpd' and ../../../afType!='evpn' and ../../../afType!='vpntarget'";
                  type boolean;
                  default "false";
                  description
                    "Whether the peer can reside in an independent peer group.";
                }
                container peerGroupAFCraPres {
                  when "../../../afType='ipv4uni'";
                  must "(../defaultRtMatchMode!='null' and count(peerGroupAFCraPre)>=1) or (../defaultRtMatchMode='null' and count(peerGroupAFCraPre)=0)";
                  description
                    "Configure the matching conditions for default route advertisement. (Only the default routes that match the conditions can be advertised.)";
                  list peerGroupAFCraPre {
                    key "defaultRtAddress defaultRtMask";
                    max-elements  "4";
                    description
                      "Configure the matching condition for default route advertisement.";
                    leaf defaultRtAddress {
                      type inet:ipv4-address-no-zone;
                      description
                        "Configure a prefix that is used to match default routes.";
                    }
                    leaf defaultRtMask {
                      type uint32 {
                        range "0..32";
                      }
                      description
                        "Configure a mask that is used to match default routes.";
                    }
                  }
                }
                container peerGroupAFCraIPv6Pres {
                  when "../../../afType='ipv6uni'";
                  must "(../defaultRtMatchMode!='null' and count(peerGroupAFCraIPv6Pre)>=1) or (../defaultRtMatchMode='null' and count(peerGroupAFCraIPv6Pre)=0)";
                  description
                    "Configure the matching conditions for default route advertisement. (Only the default routes that match the conditions can be advertised.)";
                  list peerGroupAFCraIPv6Pre {
                    key "deRtIpv6Addr deRtIPv6Mask";
                    max-elements  "4";
                    description
                      "Configure the matching condition for default route advertisement.";
                    leaf deRtIpv6Addr {
                      type inet:ipv6-address-no-zone;
                      description
                        "Configure a IPv6-prefix that is used to match default routes.";
                    }
                    leaf deRtIPv6Mask {
                      type uint32 {
                        range "0..128";
                      }
                      description
                        "Configure a mask that is used to match default routes.";
                    }
                  }
                }
                container peerAFMembers {
                  when "not(../../../afType='ipv4vpnmcast' or ../../../afType='mdt' or ../../../afType='vpntarget')";
                  config false;
                  description
                    "List of peers in the peer address family.";
                  list peerAFMember {
                    key "peer";
                    config false;
                    description
                      "Peer in the peer address family.";
                    leaf peer {
                      type string {
                        length "1..512";
                      }
                      config false;
                      description
                        "Peer address in the peer address family.";
                    }
                  }
                }
                container defOriginates {
                  when "not(../../../afType='ipv4vpnmcast' or ../../../afType='mdt' or ../../../afType='vpntarget')";
                  description
                    "List of advertised default VPNv4 routes.";
                  list defOriginate {
                    when "../../../../afType='ipv4vpn'";
                    key "configVrfName";
                    description
                      "Advertised default VPNv4 route";
                    leaf configVrfName {
                      type leafref {
                        path "/l3vpn:l3vpn/l3vpn:l3vpncomm/l3vpn:l3vpnInstances/l3vpn:l3vpnInstance/l3vpn:vrfName";
                      }
                      description
                        "VPN instance name. It uniquely identifies a VPN instance. The name is a string of case-sensitive characters.";
                    }
                  }
                }
              }
            }
            container peerAFs {
              description
                "Peers in a specified address family.";
              list peerAF {
                when "not(../../afType='mvpn' and ../../../../vrfName!='_public_')";
                key "remoteAddress";
                description
                  "Peer in a specified address family.";
                leaf remoteAddress {
                  type leafref {
                    path "../../../../../bgpPeers/bgpPeer/peerAddr";
                  }
                  description
                    "IPv4 or IPv6 peer connection address.";
                }
                leaf peerGroupName {
                  when "not(../../../afType='ipv4flow' or ../../../afType='ipv6flow' or ../../../afType='rpd' or ../../../afType='vpnv4flow' or ../../../afType='vpnv6flow') or ../../../afType!='ipv4flow' and ../../../afType!='ipv6flow'";
                  type leafref {
                    path "../../../peerGroupAFs/peerGroupAF/groupName";
                  }
                  description
                    "Configure a name for a peer group. After a peer is deleted from the peer group, the peer is disabled from the address family.";
                  ext:allowDelete "true";
                }
                leaf labelRouteCapability {
                  when "../../../afType!='ipv4multi' and ../../../afType!='ipv4vpn' and ../../../afType!='ipv6vpn' and ../../../afType!='ipv4flow' and ../../../afType!='ipv6flow' and ../../../afType!='l2vpnad' and ../../../afType!='mvpn' and ../../../afType!='evpn' and ../../../afType!='ls' and ../../../afType!='rpd' and ../../../afType!='ipv4vpnmcast' and ../../../afType!='vpntarget' and ../../../afType!='mvpnv6' and ../../../afType!='mdt' and ../../../afType!='vpnv4flow' and ../../../afType!='vpnv6flow' and ../../../afType!='ipv4labeluni'";
                  type boolean;
                  default "false";
                  description
                    "Enable a device to exchange labeled routes";
                  ext:allowDelete "true";
                }
                leaf checkTunnelReachable {
                  when "../../../afType!='ipv4multi' and ../../../afType!='ipv4vpn' and ../../../afType!='ipv6vpn' and ../../../afType!='ipv4flow' and ../../../afType!='ipv6flow' and ../../../afType!='l2vpnad' and ../../../afType!='mvpn' and ../../../afType!='evpn' and ../../../afType!='ls' and ../../../afType!='ipv4vpnmcast' and ../../../afType!='vpntarget'";
                  type boolean;
                  default "false";
                  description
                    "Enable tunnel reachability check.";
                  ext:allowDelete "true";
                }
                leaf checkWithdrawType {
                  when "../../../afType!='ipv4multi' and ../../../afType!='ipv4vpn' and ../../../afType!='ipv6vpn' and ../../../afType!='ipv4flow' and ../../../afType!='ipv6flow' and ../../../afType!='l2vpnad' and ../../../afType!='mvpn' and ../../../afType!='evpn' and ../../../afType!='ls' and ../../../afType!='rpd' and ../../../afType!='ipv4vpnmcast' and ../../../afType!='vpntarget'";
                  type boolean;
                  default "false";
                  description
                    "Enable withdraw type check.";
                  ext:allowDelete "true";
                }
                leaf advertiseIrb {
                  when "not(../../../afType='rpd' or ../../../afType='vpnv4flow' or ../../../afType='vpnv6flow') or ../../../afType='evpn'";
                  type boolean;
                  default "false";
                  description
                    "Adervertise IRB Route when its value is true.  The default value is false.";
                }
                leaf advertiseArp {
                  when "not(../../../afType='rpd' or ../../../afType='vpnv4flow' or ../../../afType='vpnv6flow') or ../../../afType='evpn'";
                  type boolean;
                  default "false";
                  description
                    "Adervertise ARP Route when its value is true.  The default value is false.";
                }
                leaf advertiseIrbv6 {
                  when "../../../afType='evpn'";
                  type boolean;
                  default "false";
                  description
                    "Adervertise IRBv6 Route when its value is true.  The default value is false.";
                }
                leaf advertiseND {
                  when "../../../afType='evpn'";
                  type boolean;
                  default "false";
                  description
                    "Adervertise ND Route when its value is true.  The default value is false.";
                }                
                leaf advertiseRemoteNexthop {
                  when "not(../../../afType='ipv4vpnmcast' or ../../../afType='ls' or ../../../afType='mdt' or ../../../afType='rpd' or ../../../afType='vpntarget' or ../../../afType='vpnv4flow' or ../../../afType='vpnv6flow') or ../../../afType='ipv4vpn'";
                  type boolean;
                  default "false";
                  description
                    "Advertise the remote nexthop to a peer or peer group. By default, the remote nexthop attribute is not advertised to any peer or peer group.";
                }
                leaf advertiseCommunity {
                  when "../../../afType!='ipv4vpnmcast' and ../../../afType!='ls' and ../../../afType!='rpd' or ../../../afType!='ls' and ../../../afType!='rpd'";
                  type boolean;
                  default "false";
                  description
                    "Advertise the community attribute to a peer or peer group. By default, the community attribute is not advertised to any peer or peer group.";
                  ext:allowDelete "true";
                }
                leaf advertiseExtCommunity {
                  when "not(../../../afType='evpn' or ../../../afType='ipv4vpnmcast' or ../../../afType='mdt' or ../../../afType='mvpn' or ../../../afType='mvpnv6' or ../../../afType='rpd' or ../../../afType='vpntarget' or ../../../afType='vpnv4flow' or ../../../afType='vpnv6flow') or ../../../afType!='ipv6vpn' and ../../../afType!='ipv4vpn' and ../../../afType!='ipv4flow' and ../../../afType!='ipv6flow' and ../../../afType!='l2vpnad' and ../../../afType!='evpn' and ../../../afType!='mvpn' and ../../../afType!='mvpnv6' and ../../../afType!='ipv4vpnmcast' and ../../../afType!='mdt' and ../../../afType!='ls' and ../../../afType!='rpd' and ../../../afType!='vpntarget'";
                  type boolean;
                  default "false";
                  description
                    "Advertise the extended community attribute to a peer or peer group. By default, the extended community attribute is not advertised to any peer or peer group.";
                  ext:allowDelete "true";
                }
                leaf discardExtCommunity {
                  when "not(../../../afType='ipv4vpnmcast' or ../../../afType='mdt' or ../../../afType='rpd' or ../../../afType='vpntarget' or ../../../afType='vpnv4flow' or ../../../afType='vpnv6flow') or ../../../afType!='ipv4vpn' and ../../../afType!='ipv6vpn' and ../../../afType!='ipv4flow' and ../../../afType!='ipv6flow' and ../../../afType!='l2vpnad' and ../../../afType!='mvpn' and ../../../afType!='mvpnv6' and ../../../afType!='evpn' and ../../../afType!='ipv4vpnmcast' and ../../../afType!='mdt' and ../../../afType!='ls' and ../../../afType!='rpd' and ../../../afType!='vpntarget'";
                  type boolean;
                  default "false";
                  description
                    "Discard the extended community attribute in the routing information about a specified peer. By default, the extended community attribute in the routing information about a specified peer is not discarded.";
                  ext:allowDelete "true";
                }
                leaf allowAsLoopEnable {
                  when "not(../../../afType='ipv4flow' or ../../../afType='ipv4vpnmcast' or ../../../afType='ipv6flow' or ../../../afType='mdt' or ../../../afType='mvpn' or ../../../afType='mvpnv6' or ../../../afType='rpd' or ../../../afType='vpnv4flow' or ../../../afType='vpnv6flow') or ../../../afType!='ipv4flow' and ../../../afType!='ipv6flow' and ../../../afType!='mvpn' and ../../../afType!='mvpnv6' and ../../../afType!='ipv4vpnmcast' and ../../../afType!='mdt' and ../../../afType!='ls' and ../../../afType!='rpd' or ../../../afType!='ipv4flow' and ../../../afType!='ipv6flow'";
                  type boolean;
                  default "false";
                  description
                    "Allow repetitive local AS numbers. By default, repetitive local AS numbers are not allowed.";
                  ext:allowDelete "true";
                }
                leaf allowAsLoopLimit {
                  when "not(../../../afType='ipv4vpnmcast' or ../../../afType='mdt' or ../../../afType='rpd' or ../../../afType='vpnv4flow' or ../../../afType='vpnv6flow') or ../../../afType!='ipv4flow' and ../../../afType!='ipv6flow' and ../../../afType!='mvpn' and ../../../afType!='mvpnv6' and ../../../afType!='ipv4vpnmcast' and ../../../afType!='mdt' and ../../../afType!='ls' and ../../../afType!='rpd' or ../allowAsLoopEnable='true'";
                  type uint32 {
                    range "1..10";
                  }
                  description
                    "with";
                  ext:allowDelete "true";
                }
                leaf keepAllRoutes {
                  when "not(../../../afType='ipv4labeluni' or ../../../afType='ipv4vpnmcast' or ../../../afType='mdt' or ../../../afType='rpd' or ../../../afType='vpntarget' or ../../../afType='vpnv4flow' or ../../../afType='vpnv6flow') or ../../../afType!='ipv4flow' and ../../../afType!='ipv6flow' and ../../../afType!='l2vpnad' and ../../../afType!='mvpn' and ../../../afType!='mvpnv6' and ../../../afType!='evpn' and ../../../afType!='ipv4vpnmcast' and ../../../afType!='mdt' and ../../../afType!='ls' and ../../../afType!='rpd' and ../../../afType!='vpntarget' and ../../../afType!='ipv4labeluni'";
                  type boolean;
                  default "false";
                  description
                    "Save all the updated information about BGP routes from a specified peer or peer group after a BGP connection is established, even though these BGP routes fail to match the routing policy on the ingress. By default, the updated information about BGP routes from a specified peer is saved only when the routes match the routing policy on the ingress. If a router supports route refreshing, this option is not required.";
                  ext:allowDelete "true";
                }
                leaf loadBalancingEnable {
                  when "not(../../../afType='ipv4vpnmcast' or ../../../afType='mdt' or ../../../afType='rpd' or ../../../afType='vpntarget' or ../../../afType='vpnv4flow' or ../../../afType='vpnv6flow') or ../../../afType!='ipv6vpn' and ../../../afType!='ipv4vpn' and ../../../afType!='ipv4flow' and ../../../afType!='ipv6flow' and ../../../afType!='l2vpnad' and ../../../afType!='evpn' and ../../../afType!='mvpn' and ../../../afType!='mvpnv6' and ../../../afType!='ipv4vpnmcast' and ../../../afType!='mdt' and ../../../afType!='ls' and ../../../afType!='rpd' and ../../../afType!='vpntarget' or ../../../afType!='mvpn' and ../../../afType!='mvpnv6' and ../../../afType!='evpn' and ../../../afType!='ipv4vpn' and ../../../afType!='ipv6vpn' and ../../../afType!='l2vpnad' and ../../../afType!='ipv4flow' and ../../../afType!='ipv6flow' and ../../../afType!='mdt' and ../../../afType!='ls' and ../../../afType!='rpd' and ../../../afType!='vpntarget'";
                  type boolean;
                  default "false";
                  description
                    "Enable a neighbour to participate in load balancing.";
                }
                leaf loadBalancingIgnoreAs {
                  when "not(../../../afType='ipv4vpnmcast' or ../../../afType='mdt' or ../../../afType='rpd' or ../../../afType='vpntarget' or ../../../afType='vpnv4flow' or ../../../afType='vpnv6flow') or ../../../afType!='mvpn' and ../../../afType!='mvpnv6' and ../../../afType!='evpn' and ../../../afType!='ipv4vpn' and ../../../afType!='ipv6vpn' and ../../../afType!='l2vpnad' and ../../../afType!='ipv4flow' and ../../../afType!='ipv6flow' and ../../../afType!='mdt' and ../../../afType!='ls' and ../../../afType!='rpd' and ../../../afType!='vpntarget' or ../loadBalancingEnable='true'";
                  type boolean;
                  default "false";
                  description
                    "Configure BGP to ignore the AS_Path attribute when selecting the equal route. By default, BGP uses the AS_Path attribute as one of route selection rules. After as-path-neglect is selected, BGP does not compare the AS_Path length.";
                }
                leaf loadBalancingRelaxAs {
                  when "not(../../../afType='ipv4vpnmcast' or ../../../afType='mdt' or ../../../afType='vpntarget') or ../../../afType!='mvpn' and ../../../afType!='mvpnv6' and ../../../afType!='evpn' and ../../../afType!='ipv4vpn' and ../../../afType!='ipv6vpn' and ../../../afType!='l2vpnad' and ../../../afType!='ipv4flow' and ../../../afType!='ipv6flow' and ../../../afType!='mdt' and ../../../afType!='ls' and ../../../afType!='rpd' and ../../../afType!='vpntarget' or ../loadBalancingEnable='true'";
                  type boolean;
                  default "false";
                  description
                    "Configure BGP to ignore comparison of AS_Path attributes with the same length when selecting the equal route. By default, BGP uses the AS_Path attribute as one of route selection rules. After as-path-neglect is selected, BGP does not compare the AS_Path length.";
                }
                leaf nextHopConfigure {
                  when "not(../../../afType!='ipv4uni' and ../../../afType!='ipv4labeluni' and ../../../afType!='ipv6uni' and ../../../afType!='ipv4vpn' and ../../../afType!='ipv6vpn' and ../../../afType!='evpn' and ../../../afType!='l2vpnad' and ../../../afType!='mvpn' and ../../../afType!='mvpnv6' and ../../../afType!='mdt' and ../../../afType!='ipv4multi' or ../../../afType='ipv4flow' or ../../../afType='ipv4vpnmcast' or ../../../afType='ipv6flow' or ../../../afType='ls' or ../../../afType='rpd' or ../../../afType='vpnv4flow' or ../../../afType='vpnv6flow') or ../../../afType='evpn'";
                  type bgpcommNextHopCfg;
                  must "(../../../afType!='ipv4uni' and ../../../afType!='ipv4labeluni' and ../../../afType!='ipv4vpn' and ../../../afType!='ipv6vpn' and ../../../afType!='l2vpnad' and ../../../afType!='evpn' and (../nextHopConfigure='null' or ../nextHopConfigure='local') ) or ((not(../../../afType!='ipv4uni' and ../../../afType!='ipv4labeluni' and ../../../afType!='ipv4vpn' and ../../../afType!='ipv6vpn' and ../../../afType!='l2vpnad' and ../../../afType!='evpn') and (../nextHopConfigure='null' or ../nextHopConfigure='local' or ../nextHopConfigure='invariable') ))";
                  description
                    "Both the next-hop-local mode and next-hop-invariable mode are available when the peer address family is the VPNv4/VPNV6/L2VPN AD address family. Only the next-hop-local mode is available when the peer address family is not VPNv4/VPNV6/L2VPN AD address family. In next-hop-local mode, you can configure a BGP speaker to set its IP address of as the next hop of the routes to be advertised to IBGP peers or IBGP peer groups. In next-hop-invariable mode, you can configure PEs in different ASs not to change the next hop of routes when the PEs advertise the routes to their EBGP peers and use the next hop addresses of IGP routes to advertise imported IGP routes to IBGP peers. By default, when a BGP speaker advertises routes to EBGP peers and imported IGP routes to IBGP peers, the BGP speaker changes the next hop to its interface address. ";
                  ext:allowDelete "true";
                }
                leaf preferredValue {
                  when "not(../../../afType='ipv4vpnmcast' or ../../../afType='mdt' or ../../../afType='rpd' or ../../../afType='vpnv4flow' or ../../../afType='vpnv6flow') or ../../../afType!='ipv4flow' and ../../../afType!='ipv6flow' and ../../../afType!='mvpn' and ../../../afType!='mvpnv6' and ../../../afType!='evpn' and ../../../afType!='ipv4vpnmcast' and ../../../afType!='mdt' and ../../../afType!='ls' and ../../../afType!='rpd'";
                  type uint32 {
                    range "0..65535";
                  }
                  default "0";
                  description
                    "Assign a preferred value for the routes learned from a specified peer. The value is an integer. By default, the preferred value of the route learnt from BGP peers is 0. After a preferred value is configured for the routes learned from a specified peer, all the routes that learnt from this peer will use this preferred value. When multiple routes reach the same address prefix, the route with the largest preferred value will be selected.";
                  ext:allowDelete "true";
                }
                leaf rtpDistributeEnable {
                  when "not(../../../afType!='ipv4flow' and ../../../afType!='ipv6flow' or ../../../afType='ls' or ../../../afType='rpd' or ../../../afType='vpnv4flow') or ../../../afType='ipv4flow' and ../../../../../vrfName='_public_'";
                  type flowRtpDistributeType;
                  must "not(../../../afType='ipv4flow' and ../../../../../vrfName='_public_') or (../../../afType='ipv4flow' and ../../../../../vrfName='_public_' and (../rtpDistributeEnable='null' or ../rtpDistributeEnable='receive') )";
                  default "null";
                  description
                    "Enable the RPD capability.";
                  ext:allowDelete "true";
                }
                leaf publicAsOnly {
                  when "not(../../../afType='evpn' or ../../../afType='ipv4flow' or ../../../afType='ipv4vpnmcast' or ../../../afType='ipv6flow' or ../../../afType='mdt' or ../../../afType='mvpn' or ../../../afType='mvpnv6' or ../../../afType='rpd' or ../../../afType='vpnv4flow' or ../../../afType='vpnv6flow') or ../../../afType!='mvpn' and ../../../afType!='mvpnv6' and ../../../afType!='ipv4flow' and ../../../afType!='ipv6flow' and ../../../afType!='evpn' and ../../../afType!='ipv4vpnmcast' and ../../../afType!='mdt' and ../../../afType!='ls' and ../../../afType!='rpd'";
                  type boolean;
                  default "false";
                  description
                    "Configure BGP to send Update packets carrying only public AS numbers. By default, private AS numbers can be carried in BGP Update packets.";
                  ext:allowDelete "true";
                }
                leaf publicAsOnlyForce {
                  when "../publicAsOnly='true' and ../publicAsOnlyLimited='false'";
                  type boolean;
                  must "(../../../afType!='mvpn' and ../../../afType!='ipv4flow' and ../../../afType!='ipv6flow' and ../../../afType!='evpn' and ../publicAsOnly='false' and ../../../afType!='ipv4vpnmcast' and ../../../afType!='mdt' and ../../../afType!='ls' and ../publicAsOnlyForce='false') or (../publicAsOnlyLimited='true' and ../publicAsOnlyForce='false') or not(../../../afType!='mvpn' and ../../../afType!='ipv4flow' and ../../../afType!='ipv6flow' and ../../../afType!='evpn' and ../publicAsOnly='false' and ../../../afType!='ipv4vpnmcast' and ../../../afType!='mdt' and ../../../afType!='ls' or ../publicAsOnlyLimited='true') or not(../publicAsOnlyForce and ../publicAsOnlyLimited and ../publicAsOnlyForce='true' and ../publicAsOnlyLimited='true')";
                  default "false";
                  description
                    "Configures BGP to carry only the public AS number instead of the private AS number when BGP sends Update packets. By default, BGP can carry the private AS number when BGP sends Update packets.";
                  ext:allowDelete "true";
                }
                leaf publicAsOnlyLimited {
                  when "../publicAsOnly='true' and ../publicAsOnlyForce='false'";
                  type boolean;
                  must "(../../../afType!='mvpn' and ../../../afType!='ipv4flow' and ../../../afType!='ipv6flow' and ../../../afType!='evpn' and ../publicAsOnly='false' and ../../../afType!='ipv4vpnmcast' and ../../../afType!='mdt' and ../../../afType!='ls' and ../publicAsOnlyLimited='false') or (../publicAsOnlyForce='true' and ../publicAsOnlyLimited='false') or not(../../../afType!='mvpn' and ../../../afType!='ipv4flow' and ../../../afType!='ipv6flow' and ../../../afType!='evpn' and ../publicAsOnly='false' and ../../../afType!='ipv4vpnmcast' and ../../../afType!='mdt' and ../../../afType!='ls' or ../publicAsOnlyForce='true') or not(../publicAsOnlyLimited and ../publicAsOnlyForce and ../publicAsOnlyLimited='true' and ../publicAsOnlyForce='true')";
                  default "false";
                  description
                    "When the BGP sends update packets, the left ends of both the local AS and public AS do not carry the private AS. By default, BGP can carry the private AS number when BGP sends Update packets.";
                  ext:allowDelete "true";
                }
                leaf publicAsOnlyReplace {
                  when "../../../afType!='mvpn' and ../../../afType!='mvpnv6' and ../../../afType!='ipv4flow' and ../../../afType!='ipv6flow' and ../../../afType!='evpn' and ../publicAsOnly='true' and ../../../afType!='ipv4vpnmcast' and ../../../afType!='mdt' and ../../../afType!='ls' and ../../../afType!='rpd'";
                  type boolean;
                  must "not(../../../afType!='mvpn' and ../../../afType!='ipv4flow' and ../../../afType!='ipv6flow' and ../../../afType!='evpn' and ../publicAsOnly='false' and ../../../afType!='ipv4vpnmcast' and ../../../afType!='mdt' and ../../../afType!='ls' and ../../../afType!='rpd') or (../../../afType!='mvpn' and ../../../afType!='ipv4flow' and ../../../afType!='ipv6flow' and ../../../afType!='evpn' and ../publicAsOnly='false' and ../../../afType!='ipv4vpnmcast' and ../../../afType!='mdt' and ../../../afType!='ls' and ../../../afType!='rpd' and ../publicAsOnlyReplace='false')";
                  default "false";
                  description
                    "When the BGP sends update packets, the private AS is replaced by the local AS. By default, BGP can carry the private AS number when BGP sends Update packets.";
                  ext:allowDelete "true";
                }
                leaf publicAsOnlySkipPeerAs {
                  when "../../../afType!='mvpn' and ../../../afType!='mvpnv6' and ../../../afType!='ipv4flow' and ../../../afType!='ipv6flow' and ../../../afType!='evpn' and ../publicAsOnly='true' and ../../../afType!='ipv4vpnmcast' and ../../../afType!='mdt' and ../../../afType!='ls' and ../../../afType!='rpd'";
                  type boolean;
                  must "not(../../../afType!='mvpn' and ../../../afType!='mvpnv6' and ../../../afType!='ipv4flow' and ../../../afType!='ipv6flow' and ../../../afType!='evpn' and ../publicAsOnly='false' and ../../../afType!='ipv4vpnmcast' and ../../../afType!='mdt' and ../../../afType!='ls' and ../../../afType!='rpd') or (../../../afType!='mvpn' and ../../../afType!='mvpnv6' and ../../../afType!='ipv4flow' and ../../../afType!='ipv6flow' and ../../../afType!='evpn' and ../publicAsOnly='false' and ../../../afType!='ipv4vpnmcast' and ../../../afType!='mdt' and ../../../afType!='ls' and ../../../afType!='rpd' and ../publicAsOnlySkipPeerAs='false')";
                  default "false";
                  description
                    "When the BGP sends update packets, the neigbour AS is not processed. By default, BGP can carry the private AS number when BGP sends Update packets.";
                  ext:allowDelete "true";
                }
                leaf routeLimit {
                  when "not(../../../afType='rpd')";
                  type uint32 {
                    range "1..4294967295";
                  }
                  description
                    "Configure the maximum number of routes that can be accepted from a peer. ";
                  ext:allowDelete "true";
                }
                leaf acceptPrefixEnable {
                  when "not(../../../afType='rpd') or ../../../afType!='ipv4flow' and ../../../afType!='ipv6flow' and ../../../afType!='vpnv4flow' and ../../../afType!='vpnv6flow' and ../../../afType!='mvpn' and ../../../afType!='mvpnv6' and ../routeLimit";
                  type boolean;
                  default "false";
                  description
                    "Enable the device to keep receiving routes and the routes are valid if the maximum number of routes allowed have been received and the alert-only parameter is specified.";
                  ext:allowDelete "true";
                }
                leaf routeLimitPercent {
                  when "../routeLimit";
                  type uint8 {
                    range "1..100";
                  }
                  default "75";
                  description
                    "Specify the percentage of routes when a router starts to generate an alarm. The default value is 75.";
                  ext:allowDelete "true";
                }
                leaf routeLimitType {
                  when "../routeLimit";
                  type bgpcommRouteLmtType;
                  default "noparameter";
                  description
                    "Set the processing method as alert-only, idle-forever, or idle-timeout when the number of routes exceeds the set threshold. When alert-only is used, only an alarm is generated when the number of routes exceeds the threshold. In this case, new routes are no longer accepted. When idle-forever is used, connections are not automatically reestablished after being cut off until BGP connections are reset if the number of routes exceeds the set threshold. When idle-timeout is used and the idle-timeout timer is specified, the connections are automatically reestablished after being cut off if the number of routes exceeds the set threshold. You can reset BGP connections to reestablish the connections before the idle-timeout times expires.";
                  ext:allowDelete "true";
                }
                leaf routeLimitIdleTimeout {
                  when "../routeLimitType='idleTimeout'";
                  type uint16 {
                    range "1..1200";
                  }
                  default "1";
                  description
                    "Specify the value of the idle-timeout timer to automatically reestablish the connections after they are cut off when the number of routes exceeds the set threshold.";
                  ext:allowDelete "true";
                }
                leaf rtUpdtInterval {
                  when "not(../../../afType='rpd' or ../../../afType='vpnv4flow' or ../../../afType='vpnv6flow') or ../../../afType!='evpn'";
                  type uint16 {
                    range "0..600";
                  }
                  description
                    "Specify the minimum interval at which Update packets are sent. The value is an integer, in seconds. By default, the interval at which Update packets are sent to IBGP peers is 15s, and the interval at which Update packets are sent to EBGP peers is 30s. When routes change, a router will send Update packets to notify its peers. If a route changes frequently, you can set an interval at which Update packets are sent to prevent the router from sending Update packets each time the route changes. This configuration is valid only to the routes learned from peers. ";
                  ext:allowDelete "true";
                }
                leaf redirectIP {
                  when "../../../afType='ipv4flow'";
                  type boolean;
                  default "false";
                  description
                    "After configuration commands, peer can handle the extended community attribute redirect-ip.";
                  ext:allowDelete "true";
                }
                leaf redirectIPVaildation {
                  when "not(../../../afType='rpd' or ../../../afType='vpnv4flow' or ../../../afType='vpnv6flow') or ../../../afType='ipv4flow'";
                  type boolean;
                  default "false";
                  description
                    "Indicate whether validation redirect ip, and this command only support ipv4-family flow address family";
                  ext:allowDelete "true";
                }
                leaf reflectClient {
                  when "../../../../../vrfName='_public_' and (../../../afType='ipv4uni' or ../../../afType='ipv4vpn' or ../../../afType='ipv6uni' or ../../../afType='ipv6vpn' or ../../../afType='ipv4labeluni')";
                  type boolean;
                  default "false";
                  description
                    "Configure the local device as a route reflector (RR) and a peer or peer group as its client. By default, the RR and its client are not configured. This configuration is applicable between IBGP peers only. The configurations of RRs and its clients in an address family are valid only in this address family. Therefore, it is recommended to configure RRs and its clients in the specified address family that is required.";
                  ext:allowDelete "true";
                }
                leaf substituteAsEnable {
                  when "not(../../../afType='rpd' or ../../../afType='vpntarget' or ../../../afType='vpnv4flow' or ../../../afType='vpnv6flow') or ../../../afType!='ipv4multi' and ../../../afType!='ipv4vpn' and ../../../afType!='ipv6vpn' and ../../../afType!='ipv4flow' and ../../../afType!='ipv6flow' and ../../../afType!='l2vpnad' and ../../../afType!='mvpn' and ../../../afType!='mvpnv6' and ../../../afType!='evpn' and ../../../afType!='ipv4vpnmcast' and ../../../afType!='mdt' and ../../../afType!='ls' and ../../../afType!='rpd' and ../../../afType!='vpntarget'";
                  type boolean;
                  default "false";
                  description
                    "Replace the AS number of a specified peer in the AS_Path attribute with the local AS number. By default, the AS number replacement is disabled. On a PE where AS number replacement is enabled, if an AS number in the AS_Path attribute of a route is same as that of the CE to which the PE advertises the route, the PE replaces the AS number with its own AS number before advertising the route.";
                  ext:allowDelete "true";
                }
                leaf importRtPolicyName {
                  when "../../../afType!='rpd'";
                  type leafref {
                    path "/rtp:rtp/rtp:routePolicys/rtp:routePolicy/rtp:name";
                  }
                  description
                    "Specify the filtering policy applied to the routes learned from a peer. By default, no such policy is specified.";
                  ext:allowDelete "true";
                }
                leaf exportRtPolicyName {
                  when "../../../afType!='rpd'";
                  type leafref {
                    path "/rtp:rtp/rtp:routePolicys/rtp:routePolicy/rtp:name";
                  }
                  description
                    "Specify the filtering policy applied to the routes to be advertised to a peer. By default, no such policy is specified.";
                  ext:allowDelete "true";
                }
                leaf sncImrtRtPolicyName {
                  when "not(../../../afType='ipv4flow' or ../../../afType='ipv4vpnmcast' or ../../../afType='ls' or ../../../afType='mdt' or ../../../afType='rpd' or ../../../afType='vpntarget' or ../../../afType='vpnv4flow' or ../../../afType='vpnv6flow')";
                  type leafref {
                    path "/rtp:rtp/rtp:routePolicys/rtp:routePolicy/rtp:name";
                  }
                  description
                    "Indicates the filtering controller policy applied to the route imported from a peer. By default, the imported routing policy of the peer is not specified.";
                  ext:allowDelete "true";
                }
                leaf ignoreBitError {
                  when "not(../../../afType='ipv4vpnmcast' or ../../../afType='mdt' or ../../../afType='rpd' or ../../../afType='vpntarget' or ../../../afType='vpnv4flow' or ../../../afType='vpnv6flow') or not(../exportRtPolicyName) and ../../../afType='ipv4vpn'";
                  type boolean;
                  default "false";
                  description
                    "Configure the peer to ignore bit error detection results when applying a route-policy.";
                  ext:allowDelete "true";
                }
                leaf importPrefFiltName {
                  when "not(../../../afType!='ipv4uni' and ../../../afType!='ipv4labeluni' and ../../../afType!='ipv4multi' and ../../../afType!='ipv4vpn' and ../../../afType!='mdt' or ../../../afType='ipv4vpnmcast' or ../../../afType='rpd' or ../../../afType='vpntarget' or ../../../afType='vpnv4flow' or ../../../afType='vpnv6flow') or ../../../afType='mdt'";
                  type leafref {
                    path "/rtp:rtp/rtp:prefixFilters/rtp:prefixFilter/rtp:name";
                  }
                  description
                    "Specify the IPv4 filtering policy applied to the routes received from a specified peer. By default, no such policy is specified.";
                  ext:allowDelete "true";
                }
                leaf importPref6FiltName {
                  when "not(../../../afType!='ipv6uni' and ../../../afType!='ipv6vpn' or ../../../afType='ipv4vpnmcast' or ../../../afType='mdt' or ../../../afType='rpd' or ../../../afType='vpntarget' or ../../../afType='vpnv4flow' or ../../../afType='vpnv6flow')";
                  type leafref {
                    path "/rtp:rtp/rtp:ipv6PrefixFilters/rtp:ipv6PrefixFilter/rtp:name";
                  }
                  description
                    "Specify the IPv6 filtering policy applied to the routes received from a specified peer. By default, no such policy is specified.";
                  ext:allowDelete "true";
                }
                leaf exportPrefFiltName {
                  when "not(../../../afType!='ipv4uni' and ../../../afType!='ipv4labeluni' and ../../../afType!='ipv4multi' and ../../../afType!='ipv4vpn' and ../../../afType!='mdt' or ../../../afType='ipv4vpnmcast' or ../../../afType='mdt' or ../../../afType='rpd' or ../../../afType='vpntarget' or ../../../afType='vpnv4flow' or ../../../afType='vpnv6flow')";
                  type leafref {
                    path "/rtp:rtp/rtp:prefixFilters/rtp:prefixFilter/rtp:name";
                  }
                  description
                    "Specify the IPv4 filtering policy applied to the routes to be advertised to a specified peer. By default, no such policy is specified.";
                  ext:allowDelete "true";
                }
                leaf exportPref6FiltName {
                  when "not(../../../afType!='ipv6uni' and ../../../afType!='ipv6vpn' or ../../../afType='ipv4vpnmcast' or ../../../afType='mdt' or ../../../afType='rpd' or ../../../afType='vpntarget' or ../../../afType='vpnv4flow' or ../../../afType='vpnv6flow')";
                  type leafref {
                    path "/rtp:rtp/rtp:ipv6PrefixFilters/rtp:ipv6PrefixFilter/rtp:name";
                  }
                  description
                    "Specify the IPv6 filtering policy applied to the routes to be advertised to a specified peer. By default, no such policy is specified.";
                  ext:allowDelete "true";
                }
                leaf importAsPathNameOrNum {
                  when "not(../../../afType='ipv4vpnmcast' or ../../../afType='mdt' or ../../../afType='rpd' or ../../../afType='vpnv4flow' or ../../../afType='vpnv6flow') or ../../../afType!='ipv4flow' and ../../../afType!='ipv6flow' and ../../../afType!='l2vpnad' and ../../../afType!='evpn' and ../../../afType!='ls' and ../../../afType!='rpd'";
                  type leafref {
                    path "/rtp:rtp/rtp:asPathFilters/rtp:asPathFilter/rtp:index";
                  }
                  description
                    "Apply an AS_Path-based filtering policy to the routes received from a specified peer. The policy can be identified with a name or number, and the number ranges from 1 to 256. By default, no such policy is specified. Therefore, all BGP routes can be accepted.";
                  ext:allowDelete "true";
                }
                leaf exportAsPathNameOrNum {
                  when "not(../../../afType='ipv4vpnmcast' or ../../../afType='mdt' or ../../../afType='rpd' or ../../../afType='vpnv4flow' or ../../../afType='vpnv6flow') or ../../../afType!='ipv4flow' and ../../../afType!='ipv6flow' and ../../../afType!='l2vpnad' and ../../../afType!='evpn' and ../../../afType!='ls' and ../../../afType!='rpd'";
                  type leafref {
                    path "/rtp:rtp/rtp:asPathFilters/rtp:asPathFilter/rtp:index";
                  }
                  description
                    "Apply an AS_Path-based filtering policy to the routes to be advertised to a specified peer. The policy can be identified with a name or number, and the number ranges from 1 to 256. By default, no such policy is specified. Therefore, all BGP routes can be advertised.";
                  ext:allowDelete "true";
                }
                leaf importAclNameOrNum {
                  when "not(../../../afType!='ipv4uni' and ../../../afType!='ipv4labeluni' and ../../../afType!='ipv4multi' and ../../../afType!='ipv4vpn' and ../../../afType!='mdt' or ../../../afType='ipv4vpnmcast' or ../../../afType='rpd' or ../../../afType='vpntarget' or ../../../afType='vpnv4flow' or ../../../afType='vpnv6flow') or ../../../afType='mdt'";
                  type leafref {
                    path "/acl:acl/acl:aclGroups/acl:aclGroup/acl:aclNumOrName";
                  }
                  description
                    "Apply an IPv4 ACL-based filtering policy to the routes received from a specified peer. The ACL number ranges from 2000 to 2999, and the name must start with a letter. By default, no such policy is specified. Therefore, all BGP routes can be accepted.";
                  ext:allowDelete "true";
                }
                leaf importAcl6NameOrNum {
                  when "not(../../../afType!='ipv6uni' and ../../../afType!='ipv6vpn' or ../../../afType='ipv4vpnmcast' or ../../../afType='mdt' or ../../../afType='rpd' or ../../../afType='vpntarget' or ../../../afType='vpnv4flow' or ../../../afType='vpnv6flow')";
                  type leafref {
                    path "/acl:acl/acl:aclGroup6s/acl:aclGroup6/acl:aclNumOrName";
                  }
                  description
                    "Apply an IPv6 ACL-based filtering policy to the routes received from a specified peer. The ACL number ranges from 2000 to 2999, and the name must start with a letter. By default, no such policy is specified. Therefore, all BGP routes can be accepted.";
                  ext:allowDelete "true";
                }
                leaf exportAclNameOrNum {
                  when "not(../../../afType!='ipv4uni' and ../../../afType!='ipv4labeluni' and ../../../afType!='ipv4multi' and ../../../afType!='ipv4vpn' and ../../../afType!='mdt' or ../../../afType='ipv4vpnmcast' or ../../../afType='mdt' or ../../../afType='rpd' or ../../../afType='vpntarget' or ../../../afType='vpnv4flow' or ../../../afType='vpnv6flow')";
                  type leafref {
                    path "/acl:acl/acl:aclGroups/acl:aclGroup/acl:aclNumOrName";
                  }
                  description
                    "Apply an IPv4 ACL-based filtering policy to the routes to be advertised to a specified peer. The ACL number ranges from 2000 to 2999, and the name must start with a letter. By default, no such policy is specified. Therefore, all BGP routes can be advertised.";
                  ext:allowDelete "true";
                }
                leaf exportAcl6NameOrNum {
                  when "not(../../../afType!='ipv6uni' and ../../../afType!='ipv6vpn' or ../../../afType='ipv4vpnmcast' or ../../../afType='mdt' or ../../../afType='rpd' or ../../../afType='vpntarget' or ../../../afType='vpnv4flow' or ../../../afType='vpnv6flow')";
                  type leafref {
                    path "/acl:acl/acl:aclGroup6s/acl:aclGroup6/acl:aclNumOrName";
                  }
                  description
                    "Apply an IPv6 ACL-based filtering policy to the routes to be advertised to a specified peer. The ACL number ranges from 2000 to 2999, and the name must start with a letter. By default, no such policy is specified. Therefore, all BGP routes can be advertised.";
                  ext:allowDelete "true";
                }
                leaf ipprefixOrfEnable {
                  when "../../../../../vrfName='_public_' and ../../../afType='ipv4uni'";
                  type boolean;
                  must "not(../isNonstdIpprefixMod='true' and ../ipprefixOrfEnable='true')";
                  default "false";
                  description
                    "Enable Prefix-based BGP outbound route filtering (ORF). By default, this function is not enabled. ORF enables a BGP device to use the import policy of a peer as the local export policy so that unwanted routes are filtered out during route advertisement.";
                  ext:allowDelete "true";
                }
                leaf isNonstdIpprefixMod {
                  when "../../../../../vrfName='_public_' and ../../../afType='ipv4uni'";
                  type boolean;
                  must "not(../isNonstdIpprefixMod='true' and ../ipprefixOrfEnable='true')";
                  default "false";
                  description
                    "Enable Huawei routers to be compatible with Nonstandard routers. The ORF capability codes supported by Nonstandard devices are different from that defined by the associated RFC standard. After the option is selected, Huawei devices and Nonstandard devices negotiate ORF capability based on the ORF capability code supported by Nonstandard devices. If the option is not selected, Huawei devices and Nonstandard devices negotiate ORF capability based on the ORF capability code specified by the RFC standard.";
                  ext:allowDelete "true";
                }
                leaf orftype {
                  when "not(../../../afType='ipv4labeluni' or ../../../afType='ipv4vpnmcast' or ../../../afType='mdt' or ../../../afType='rpd' or ../../../afType='vpntarget' or ../../../afType='vpnv4flow' or ../../../afType='vpnv6flow') or ../../../afType='ipv4uni'";
                  type uint16;
                  default "0";
                  description
                    "ORF Type.";
                }
                leaf orfMode {
                  when "../../../../../vrfName='_public_' and ../../../afType='ipv4uni'";
                  type bgpcommonOrfMode;
                  must "(../ipprefixOrfEnable!='true' and ../isNonstdIpprefixMod!='true' and (../orfMode='null') ) or ((not(../ipprefixOrfEnable!='true' and ../isNonstdIpprefixMod!='true') and (../orfMode='receive' or ../orfMode='send' or ../orfMode='both') ))";
                  default "null";
                  description
                    "Configure an outbound route filtering (ORF) mode, which can be Receive, Send, or Both, and the default ORF mode is Both. ";
                  ext:allowDelete "true";
                }
                leaf soostring {
                  when "not(../../../afType='ipv4vpnmcast' or ../../../afType='mdt' or ../../../afType='rpd' or ../../../afType='vpntarget' or ../../../afType='vpnv4flow' or ../../../afType='vpnv6flow') or ../../../../../vrfName!='_public_' or ../../../afType!='ipv4multi' and ../../../afType!='ipv4vpn' and ../../../afType!='ipv6vpn' and ../../../afType!='ipv4flow' and ../../../afType!='ipv6flow' and ../../../afType!='l2vpnad' and ../../../afType!='mvpn' and ../../../afType!='mvpnv6' and ../../../afType!='evpn' and ../../../../../vrfName!='_public_' or ../../../afType!='ipv4multi' and ../../../afType!='ipv4vpn' and ../../../afType!='ipv6vpn' and ../../../afType!='ipv4flow' and ../../../afType!='ipv6flow' and ../../../afType!='l2vpnad' and ../../../afType!='mvpn' and ../../../afType!='mvpnv6' and ../../../afType!='evpn' and ../../../afType!='ipv4vpnmcast' and ../../../afType!='mdt' and ../../../afType!='ls' and ../../../afType!='rpd' and ../../../afType!='vpntarget'";
                  type string {
                    length "3..21";
                  }
                  description
                    "Configure the Site-of-Origin (SoO) extended community attribute. This attribute can be expressed in the following formats: X.X.X.X:number<0-65535>, number<0-65535>:number<0-4294967295>, or number<0-65535>.number<0-65535>:number<0-65535>  or <65536-4294967295>:<0-65535>. 0:0 or 0.0:0 is not supported. 
Two CEs are in the same site and can advertise routes to each other, and they are connected to a VPN through PEs. If the local routes of a CE are advertised to the other CE over the VPN, a routing loop may occur. 
The SoO feature can prevent a route advertised by a site from being sent back to the site, preventing routing loops. After SoO is enabled and a PE receives a route from a CE, the specified SoO attribute will be added to the route. Before advertising the route to the other CE, the PE checks the SoO attribute. If the SoO attribute is the same as the locally configured SoO attribute, the PE does not advertise the route, preventing routing loops. ";
                  ext:allowDelete "true";
                }
                leaf defaultRtAdvEnable {
                  when "not(../../../afType!='ipv4uni' and ../../../afType!='ipv4multi' and ../../../afType!='ipv6uni' and ../../../afType!='vpntarget' or ../../../afType='ipv4labeluni' or ../../../afType='ipv4vpnmcast' or ../../../afType='mdt' or ../../../afType='rpd' or ../../../afType='vpnv4flow' or ../../../afType='vpnv6flow')";
                  type boolean;
                  default "false";
                  description
                    "Enable a device to advertise the default route to its peers. By default, the device does not advertise the default route to any peer or peer group. This option enables a device to send a default route with the device as the next hop address to its peers, regardless of whether there is a default route in the local routing table.";
                  ext:allowDelete "true";
                }
                leaf defaultRtAdvPolicy {
                  when "not(../../../afType!='ipv4uni' and ../../../afType!='ipv4multi' and ../../../afType!='ipv6uni' and ../../../afType!='vpntarget' or ../../../afType!='ipv4vpn' and ../../../afType!='ipv6vpn' and ../../../afType!='ipv4flow' and ../../../afType!='ipv6flow' and ../../../afType!='l2vpnad' and ../../../afType!='mvpn' and ../../../afType!='mvpnv6' and ../../../afType!='evpn' and ../../../afType!='ipv4vpnmcast' and ../../../afType!='mdt' and ../../../afType!='ls' and ../../../afType!='rpd' and ../defaultRtAdvEnable='false' or ../../../afType='ipv4labeluni' or ../../../afType='ipv4vpnmcast' or ../../../afType='mdt' or ../../../afType='rpd' or ../../../afType='vpntarget' or ../../../afType='vpnv4flow' or ../../../afType='vpnv6flow') or ../../../afType!='ipv4vpn' and ../../../afType!='ipv6vpn' and ../../../afType!='ipv4flow' and ../../../afType!='ipv6flow' and ../../../afType!='l2vpnad' and ../../../afType!='mvpn' and ../../../afType!='mvpnv6' and ../../../afType!='evpn' and ../../../afType!='ipv4vpnmcast' and ../../../afType!='mdt' and ../../../afType!='ls' and ../../../afType!='rpd' and ../../../afType!='vpntarget' and ../../../afType!='ipv4labeluni' and ../defaultRtAdvEnable='true'";
                  type leafref {
                    path "/rtp:rtp/rtp:routePolicys/rtp:routePolicy/rtp:name";
                  }
                  description
                    "Specify the name of a used policy. The value is a string.";
                  ext:allowDelete "true";
                }
                leaf defaultRtMatchMode {
                  when "not(../../../afType='ipv4labeluni' or ../../../afType='ipv4multi' or ../../../afType='ipv4vpnmcast' or ../../../afType='mdt' or ../../../afType='rpd' or ../../../afType='vpntarget' or ../../../afType='vpnv4flow' or ../../../afType='vpnv6flow') or ../../../afType!='ipv4vpn' and ../../../afType!='ipv6vpn' and ../../../afType!='l2vpnad' and ../../../afType!='mvpn' and ../../../afType!='mvpnv6' and ../../../afType!='mdt' and ../../../afType!='evpn' and ../../../afType!='ipv4flow' and ../../../afType!='ipv6flow' and ../../../afType!='ipv4vpnmcast' and ../../../afType!='ls' and ../../../afType!='rpd' and ../../../afType!='vpntarget' and ../../../afType!='ipv4labeluni' and ../defaultRtAdvEnable='true'";
                  type bgpcommonCraMatchMode;
                  default "null";
                  description
                    "Configure the matching mode of default route advertisement, which can be disabling of route advertisement conditions, enabling of all route advertisement conditions, and enabling of part route advertisement conditions. Enabling of all route advertisement conditions indicates that a default route can be advertised only when it matches all the conditions. Enabling of part route advertisement conditions indicates that a default route can be advertised only when it matches one condition.";
                  ext:allowDelete "true";
                }
                leaf validationDisable {
                  when "not(../../../afType!='ipv4flow' and ../../../afType!='ipv6flow' or ../../../afType='ipv4vpnmcast' or ../../../afType='ls' or ../../../afType='mdt' or ../../../afType='vpntarget') or ../../../afType='ipv4flow' or ../../../afType='ipv6flow'";
                  type boolean;
                  default "false";
                  description
                    "Disable route validation.";
                  ext:allowDelete "true";
                }
                leaf upeEnable {
                  when "not(../../../afType='ipv4vpnmcast' or ../../../afType='mdt' or ../../../afType='rpd' or ../../../afType='vpntarget' or ../../../afType='vpnv4flow' or ../../../afType='vpnv6flow') or ../../../afType='ipv4vpn'";
                  type boolean;
                  default "false";
                  description
                    "Configure the peer as an underlayer PE (UPE). ";
                  ext:allowDelete "true";
                }
                leaf tnlPolicyName {
                  when "not(../../../afType='ipv4vpnmcast' or ../../../afType='mdt' or ../../../afType='rpd' or ../../../afType='vpntarget' or ../../../afType='vpnv4flow' or ../../../afType='vpnv6flow') or ../../../afType='ipv6uni'";
                  type leafref {
                    path "/tnlm:tnlm/tnlm:tunnelPolicys/tnlm:tunnelPolicy/tnlm:tnlPolicyName";
                  }
                  description
                    "Apply a tunnel policy for a 6PE peer. By default, no tunnel policy is configured.";
                  ext:allowDelete "true";
                }
                leaf advBestExternal {
                  when "../../../../../vrfName='_public_' and (../../../afType='ipv4uni' or ../../../afType='ipv4vpn' or ../../../afType='ipv6uni' or ../../../afType='ipv6vpn' or ../../../afType='ipv4labeluni')";
                  type boolean;
                  must "not(../reflectClient='true' and ../advBestExternal='true')";
                  must "not((../addPathMode and ../addPathMode!='null') and ../advBestExternal='true')";
                  must "not(../advAddPathNum and ../advBestExternal='true')";
                  default "false";
                  description
                    "Enable the device to advertise Best External routes to peers.";
                }
                leaf addPathMode {
                  when "../../../../../vrfName='_public_' and (../../../afType='ipv4uni' or ../../../afType='ipv4vpn' or ../../../afType='ipv6uni' or ../../../afType='ipv6vpn' or ../../../afType='ipv4labeluni')";
                  type bgpcommAddPathCapType;
                  default "null";
                  description
                    "Enable Add-Path route advertisement to a peer.";
                  ext:allowDelete "true";
                }
                leaf advAddPathNum {
                  when "../../../../../vrfName='_public_' and (../../../afType='ipv4uni' or ../../../afType='ipv4vpn' or ../../../afType='ipv6uni' or ../../../afType='ipv6vpn' or ../../../afType='ipv4labeluni')";
                  type uint8 {
                    range "2..64";
                  }
                  description
                    "Number of Add-Path routes that can be advertised to a peer.";
                  ext:allowDelete "true";
                }
                leaf originAsValid {
                  when "not(../../../afType='ipv4flow' or ../../../afType='ipv4labeluni' or ../../../afType='ipv4vpnmcast' or ../../../afType='ls' or ../../../afType='mdt' or ../../../afType='mvpn' or ../../../afType='mvpnv6' or ../../../afType='rpd' or ../../../afType='vpntarget' or ../../../afType='vpnv4flow' or ../../../afType='vpnv6flow' or ../advertiseExtCommunity='false' and ../../../afType='ipv4uni' or ../advertiseExtCommunity='false' and ../../../afType='ipv6flow' or ../advertiseExtCommunity='false' and ../../../afType='ipv6uni') or ../advertiseExtCommunity='true' and ../../../afType!='ipv4multi' and ../../../afType!='ipv4flow' and ../../../afType!='ipv6flow' and ../../../afType!='l2vpnad' and ../../../afType!='mvpn' and ../../../afType!='mvpnv6' and ../../../afType!='evpn' and ../../../afType!='ipv4vpnmcast' and ../../../afType!='mdt' and ../../../afType!='ls' and ../../../afType!='rpd' and ../../../afType!='vpntarget' or ../advertiseExtCommunity='true' and ../../../afType='ipv6uni'";
                  type boolean;
                  default "false";
                  description
                    "Advertises the BGP origin AS validation result to the specified BGP peer or peer group.";
                  ext:allowDelete "true";
                }
                leaf expMode {
                  when "not(../../../afType='evpn' or ../../../afType='ipv4labeluni' or ../../../afType='ipv4vpnmcast' or ../../../afType='mdt' or ../../../afType='mvpn' or ../../../afType='mvpnv6' or ../../../afType='rpd' or ../../../afType='vpntarget' or ../../../afType='vpnv4flow' or ../../../afType='vpnv6flow') or ../../../afType!='ipv4multi' and ../../../afType!='ipv4vpn' and ../../../afType!='ipv6vpn' and ../../../afType!='ipv4flow' and ../../../afType!='ipv6flow' and ../../../afType!='l2vpnad' and ../../../afType!='ipv4flow' and ../../../afType!='ipv6flow' and ../../../afType!='evpn' and ../../../afType!='mdt' and ../../../afType!='ls' and ../../../afType!='rpd' and ../../../afType!='vpntarget'";
                  type bgpcommExpModeType;
                  default "null";
                  description
                    "Specify the ASs in which a BGP label can inherit the QoS priority carried in the outer label of public tunnel in the Core AS and the ASs in which the priorities of BGP LSPs must be restored before the LSPs are advertised to a non-core AS.";
                  ext:allowDelete "true";
                }
                leaf vplsEnable {
                  when "not(../../../afType!='l2vpnad' or ../../../afType='ipv4vpnmcast' or ../../../afType='mdt' or ../../../afType='rpd' or ../../../afType='vpntarget' or ../../../afType='vpnv4flow' or ../../../afType='vpnv6flow')";
                  type boolean;
                  default "false";
                  description
                    "Enable Virtual Private LAN Services";
                  ext:allowDelete "true";
                }
                leaf vplsAdDisable {
                  when "not(../../../afType!='l2vpnad' or ../../../afType='ipv4vpnmcast' or ../../../afType='mdt' or ../../../afType='rpd' or ../../../afType='vpntarget' or ../../../afType='vpnv4flow' or ../../../afType='vpnv6flow')";
                  type boolean;
                  default "false";
                  description
                    "Enable Virtual private LAN service auto-discovery.Not receive BGP-AD Route.";
                  ext:allowDelete "true";
                }
                leaf vpwsEnable {
                  when "not(../../../afType!='l2vpnad' or ../../../afType='rpd' or ../../../afType='vpnv4flow' or ../../../afType='vpnv6flow')";
                  type boolean;
                  default "false";
                  description
                    "Enable Virtual Private Wire Services";
                  ext:allowDelete "true";
                }
                leaf updatePktStandardCompatible {
                  when "not(../../../afType='rpd' or ../../../afType='vpnv4flow' or ../../../afType='vpnv6flow') or ../../../afType='ipv4vpnmcast'";
                  type boolean;
                  default "false";
                  description
                    "Compatible Standard update packet";
                  ext:allowDelete "true";
                }
                leaf aigp {
                  when "not(../../../../../vrfName!='_public_' or ../../../afType!='ipv4uni' and ../../../afType!='ipv4vpn' and ../../../afType!='ipv6uni' and ../../../afType!='ipv6vpn' and ../../../afType!='ipv4labeluni' or ../../../afType='vpnv6flow')";
                  type boolean;
                  default "false";
                  description
                    "Enable route with AIGP attribute advertisement to or from a peer.";
                  ext:allowDelete "true";
                }
                leaf advertiseEncapType {
                  when "not(../../../afType='rpd' or ../../../afType='vpnv4flow' or ../../../afType='vpnv6flow') or ../../../afType='evpn'";
                  type advertiseEncapType;
                  default "mpls";
                  description
                    "Encapsulation type of packets.";
                  ext:allowDelete "true";
                }
                leaf reoriginatedRtEnable {
                  when "../../../afType!='ipv4flow' and ../../../afType!='ipv6flow' and ../../../afType!='ipv4multi' and ../../../afType!='ipv4uni' and ../../../afType!='ipv4labeluni' and ../../../afType!='ipv6uni' and ../../../afType!='ipv6vpn' and ../../../afType!='l2vpnad' and ../../../afType!='mvpn' and ../../../afType!='ipv4vpnmcast' and ../../../afType!='mdt' and ../../../afType!='ls' and ../../../afType!='rpd' and ../../../afType!='vpntarget' and ../../../afType!='vpnv4flow' and ../../../afType!='vpnv6flow' and ../../../afType!='mvpnv6'";
                  type boolean;
                  default "false";
                  description
                    "Enable route regeneration.";
                }
                leaf macIpRtEnable {
                  when "../../../afType!='ipv4flow' and ../../../afType!='ipv6flow' and ../../../afType!='ipv4multi' and ../../../afType!='ipv4uni' and ../../../afType!='ipv4labeluni' and ../../../afType!='ipv6uni' and ../../../afType!='ipv6vpn' and ../../../afType!='l2vpnad' and ../../../afType!='mvpn' and ../../../afType!='ipv4vpnmcast' and ../../../afType!='mdt' and ../../../afType!='ls' and ../../../afType!='rpd' and ../../../afType!='vpntarget' and ../../../afType!='vpnv4flow' and ../../../afType!='vpnv6flow' and ../../../afType!='mvpnv6'";
                  type boolean;
                  default "false";
                  description
                    "Enable MAC-IP route regeneration and advertisement.";
                }
                leaf macRtEnable {
                  when "not(../../../afType='rpd' or ../../../afType='vpnv4flow' or ../../../afType='vpnv6flow') or ../../../afType='evpn'";
                  type boolean;
                  default "false";
                  description
                    "Enable MAC route regeneration and advertisement.";
                }
                leaf ipRtEnable {
                  when "not(../../../afType!='ipv4vpn' and ../../../afType!='evpn')";
                  type boolean;
                  default "false";
                  description
                    "Enable IP route regeneration and advertisement.";
                }
                leaf vpnv4RtEnable {
                  when "not(../../../afType='rpd' or ../../../afType='vpnv4flow' or ../../../afType='vpnv6flow') or ../../../afType='evpn'";
                  type boolean;
                  default "false";
                  description
                    "Enable VPNv4 route regeneration and advertisement.";
                }
                leaf reoriginatedRtEnableDc {
                  when "not(../../../afType='rpd' or ../../../afType='vpnv4flow' or ../../../afType='vpnv6flow') or ../../../afType='evpn'";
                  type boolean;
                  default "false";
                  description
                    "Enable route regeneration.";
                }
                leaf macIpRtEnableDc {
                  when "not(../../../afType='rpd' or ../../../afType='vpnv4flow' or ../../../afType='vpnv6flow') or ../../../afType='evpn'";
                  type boolean;
                  default "false";
                  description
                    "Enable MAC-IP route regeneration and advertisement.";
                }
                leaf ipRtEnableDc {
                  when "not(../../../afType='rpd' or ../../../afType='vpnv4flow' or ../../../afType='vpnv6flow') or ../../../afType='evpn'";
                  type boolean;
                  default "false";
                  description
                    "Enable IP route regeneration and advertisement.";
                }
                leaf allowClusterCap {
                  when "not(../../../afType='ipv4flow' or ../../../afType='rpd' or ../../../afType='vpnv4flow' or ../../../afType='vpnv6flow') or ../../../afType='vpntarget'";
                  type boolean;
                  default "false";
                  description
                    "allowClusterCap";
                  ext:allowDelete "true";
                }
                leaf allowClusterNum {
                  when "not(../../../afType='rpd' or ../../../afType='vpnv4flow' or ../../../afType='vpnv6flow') or ../../../afType='vpntarget' or ../allowClusterCap='true'";
                  type uint8 {
                    range "1..10";
                  }
                  description
                    "allowClusterNum";
                  ext:allowDelete "true";
                }
                leaf advCmulMatNhp {
                  when "not(../../../afType!='mvpn' and ../../../afType!='mvpnv6')";
                  type boolean;
                  default "false";
                  description
                    "enable advertise C-multicast route directional, only advertise to the neighbor which is matched the nexthop in intra-AD route.";
                  ext:allowDelete "true";
                }
                leaf esadCompatible {
                  when "../../../afType='evpn'";
                  type esadCompatibleType;
                  default "default";
                  description
                    "Ethernet A-D per ES Route Compatible.";
                  ext:allowDelete "true";
                }
                leaf splitGroupName {
                  when "../../../afType='evpn'";
                  type string {
                    length "1..31";
                  }
                  description
                    "Split group name.";
                  ext:allowDelete "true";
                }
                leaf redirectIPRfcCompatible {
                  when "not(../../../afType!='ipv4flow' and ../../../afType!='vpnv4flow' or ../../../afType='vpnv4flow' and ../../../afType='vpnv4flow' and ../redirctDraftCompatible='true') or ../../../afType='ipv4flow' or ../../../afType='vpnv4flow'";
                  type boolean;
                  default "false";
                  description
                    "sent both  number for the apply redirect ipv4 action.";
                  ext:allowDelete "true";
                }
                leaf redirctDraftCompatible {
                  when "not(../../../afType!='ipv4flow' and ../../../afType!='vpnv4flow' or ../../../afType='ipv4flow' and ../../../afType='vpnv4flow' and ../redirectIPRfcCompatible='true') or ../../../afType='ipv4flow' or ../../../afType='vpnv4flow'";
                  type boolean;
                  default "false";
                  description
                    "sent both  number for the apply redirect ipv4 action.";
                  ext:allowDelete "true";
                }
                leaf prefixSidEnable {
                  when "../../../afType='ipv4vpn'";
                  type boolean;
                  default "false";
                  description
                    "Enable prefixSid to a peer.";
                }
                leaf staticGrTimerValue {
                  when "not(../../../afType!='ipv4flow' and ../../../afType!='ipv6flow' and ../../../afType!='vpnv4flow' and ../../../afType!='vpnv6flow' and ../../../afType!='rpd' and ../../../afType!='evpn')";
                  type uint32 {
                    range "3600..86400";
                  }
                  description
                    "Specifies the maximum time during which a peer waits for a BGP session reestablishment. in seconds.";
                  ext:allowDelete "true";
                }
                leaf expRpdPolicyEn {
                  when "../../../afType!='ipv4multi' and ../../../afType!='ipv4vpn' and ../../../afType!='ipv6vpn' and ../../../afType!='ipv4flow' and ../../../afType!='ipv6flow' and ../../../afType!='l2vpnad' and ../../../afType!='mvpn' and ../../../afType!='evpn' and ../../../afType!='ls' and ../../../afType!='rpd' and ../../../afType!='ipv4vpnmcast' and ../../../afType!='vpntarget' and ../../../afType!='mvpnv6' and ../../../afType!='mdt' and ../../../afType!='vpnv4flow' and ../../../afType!='vpnv6flow' and ../../../afType!='ipv4labeluni' and ../../../afType!='ipv6uni'";
                  type individualEnableType;
                  default "default";
                  description
                    "Enable the RPD export policy.";
                }
                leaf privateNexthop {
                  when "../../../afType='ipv4vpn'";
                  type boolean;
                  default "false";
                  description
                    "Configure a device to receive VPNv4 routes that are iterated to VPN IP addresses based on next hops instead of being iterated to a tunnel.";
                }
		leaf nhpStaticRtEnable {
                  when "../../../afType='ipv4uni'";
                  type boolean;
                  must "../nextHopConfigure='invariable' or (not(../nextHopConfigure='invariable') and ../nhpStaticRtEnable='false')";
                  default "false";
                  description
                    "Static route enable for next-hop-invariable.";
                  ext:allowDelete "true";
                }
				leaf upgCfgIndependent  {
                  when "../../../afType!='rpd' and ../../../afType!='evpn' and ../../../afType!='vpntarget'";
                  type bgpcommPeerIdpEnable;
                  default "default";
                  description
                    "Whether the peer can reside in an independent peer group.";
                }
				leaf upgEffectIndependent  {
                  when "../../../afType!='rpd' and ../../../afType!='evpn' and ../../../afType!='vpntarget'";
                  type boolean;
                  default "false";
				  config false;
                  description
                    "Enable the peer to reside in an independent peer group.";
                }
                container peerAFCraPres {
                  when "../../../afType='ipv4uni'";
                  must "(../defaultRtMatchMode!='null' and count(peerAFCraPre)>=1) or (../defaultRtMatchMode='null' and count(peerAFCraPre)=0)";
                  description
                    "Configure the matching conditions for default route advertisement. (Only the default routes that match the conditions can be advertised.)";
                  list peerAFCraPre {
                    key "defaultRtAddress defaultRtMask";
                    max-elements  "4";
                    description
                      "Configure the matching condition for default route advertisement.";
                    leaf defaultRtAddress {
                      type inet:ipv4-address-no-zone;
                      description
                        "Configure a prefix that is used to match default routes.";
                    }
                    leaf defaultRtMask {
                      type uint32 {
                        range "0..32";
                      }
                      description
                        "Configure a mask that is used to match default routes.";
                    }
                  }
                }
                container peerAFCraIPv6Pres {
                  when "../../../afType='ipv6uni'";
                  must "(../defaultRtMatchMode!='null' and count(peerAFCraIPv6Pre)>=1) or (../defaultRtMatchMode='null' and count(peerAFCraIPv6Pre)=0)";
                  description
                    "Configure the matching conditions for default route advertisement. (Only the default routes that match the conditions can be advertised.)";
                  list peerAFCraIPv6Pre {
                    key "deRtIpv6Addr deRtIPv6Mask";
                    max-elements  "4";
                    description
                      "Configure the matching condition for default route advertisement.";
                    leaf deRtIpv6Addr {
                      type inet:ipv6-address-no-zone;
                      description
                        "Configure a IPv6-prefix that is used to match default routes.";
                    }
                    leaf deRtIPv6Mask {
                      type uint32 {
                        range "0..128";
                      }
                      description
                        "Configure a mask that is used to match default routes.";
                    }
                  }
                }
                container statisticsInfo {
                  config false;
                  description
                    "Route statistics.";
                  leaf recvNLRINum {
                    type uint32 {
                      range "0..4294967295";
                    }
                    config false;
                    description
                      "Number of reachable routes.";
                  }
                  leaf recvUNLRINum {
                    type uint32 {
                      range "0..4294967295";
                    }
                    config false;
                    description
                      "Number of unreachable routes.";
                  }
                  leaf prePlyRouteNum {
                    type uint32 {
                      range "0..4294967295";
                    }
                    config false;
                    description
                      "Number of accepted routes.";
                  }
                  leaf postPlyRouteNum {
                    type uint32 {
                      range "0..4294967295";
                    }
                    config false;
                    description
                      "Number of received routes.";
                  }
                  leaf bestRouteNum {
                    type uint32 {
                      range "0..4294967295";
                    }
                    config false;
                    description
                      "Number of optimal routes.";
                  }
                  leaf rejectedRtNum {
                    type uint32 {
                      range "0..4294967295";
                    }
                    config false;
                    description
                      "Number of rejected routes.";
                  }
                  leaf asPathLoopRtNum {
                    type uint32 {
                      range "0..4294967295";
                    }
                    config false;
                    description
                      "Number of routing loops in an AS.";
                  }
                  leaf asConfLoopRtNum {
                    type uint32 {
                      range "0..4294967295";
                    }
                    config false;
                    description
                      "Number of routing loops in an AS confederation.";
                  }
                  leaf cluLoopRtNum {
                    type uint32 {
                      range "0..4294967295";
                    }
                    config false;
                    description
                      "Number of routing loops in a cluster.";
                  }
                  leaf invalOrigRtNum {
                    type uint32 {
                      range "0..4294967295";
                    }
                    config false;
                    description
                      "Number of routes with an invalid originator ID.";
                  }
                }
                container peerInfo {
                  config false;
                  description
                    "Peer information.";
                  leaf peerType {
                    type bgpcommPeerTypeInfo;
                    config false;
                    description
                      "Configures the type of BGP peers: IBGP or EBGP.";
                  }
                  leaf version {
                    type uint8;
                    config false;
                    description
                      "The current BGP version is BGP-4. BGP-4 provides a set of new mechanisms to support Classless Inter-Domain Routing (CIDR). The new mechanisms also support the network prefix-based advertisement, cancellation of the 'class' concept for a BGP network during the network prefix-supported advertisements, and route summarization and AS path summarization.";
                  }
                  leaf remoteRouterId {
                    type inet:ipv4-address-no-zone;
                    config false;
                    description
                      "Router ID for a peer.";
                  }
                  leaf bgpCurState {
                    type bgpcommPEERSTATE;
                    config false;
                    description
                      "Current BGP state, which can be Idle, Active, Established, Connect, OpenSent, or OpenConfirm.
Idle: In this state, BGP denies all connection requests. This is the initial state of BGP.
Active: In this state, BGP tries to establish TCP connections. This is the intermediate state of BGP.
Established: In this state, BGP peers can exchange Update, Notification, and Keepalive packets with each other.
Connect: In this state, BGP determines the subsequent operation after the TCP connections are established.
OpenSent: In this state, BGP is waiting for the Open packet from the peer.
OpenConfirm: In this state, BGP is waiting for a Notification packet and a Keepalive packet.";
                  }
                  leaf localPort {
                    type uint32;
                    config false;
                    description
                      "Local port number. BGP uses the TCP as the transport layer protocol, and the port number is 179.";
                  }
                  leaf remotePort {
                    type uint32 {
                      range "0..4294967295";
                    }
                    config false;
                    description
                      "Port number for a peer to establish a peer relationship.";
                  }
                  leaf currentEvent {
                    type string {
                      length "1..39";
                    }
                    config false;
                    description
                      "Recent event that occurs on a peer.";
                  }
                  leaf bgpLastState {
                    type bgpcommPEERSTATE;
                    config false;
                    description
                      "Last state of a peer, which can be Idle, Connect, Active, OpenSent, OpenConfirm, or Established.";
                  }
                  leaf upDownDuration {
                    type string {
                      length "1..49";
                    }
                    config false;
                    description
                      "Period during which a BGP session is in the established state.";
                  }
                  leaf messageSent {
                    type uint32 {
                      range "0..4294967295";
                    }
                    config false;
                    description
                      "Number of packets sent to a peer.";
                  }
                  leaf peerRpdCapability {
                    type flowRtpDistributeType;
                    config false;
                    description
                      "Peer RPD capability.";
                  }
                  leaf localRpdCapability {
                    type flowRtpDistributeType;
                    config false;
                    description
                      "Local RPD capability.";
                  }
                  leaf negotiatedRpdCapability {
                    type flowRtpDistributeType;
                    config false;
                    description
                      "Negotiated RPD capability.";
                  }
                  leaf messageReceived {
                    type uint32 {
                      range "0..4294967295";
                    }
                    config false;
                    description
                      "Number of packets received from a peer.";
                  }
                  leaf outQueue {
                    type uint32 {
                      range "0..4294967295";
                    }
                    config false;
                    description
                      "Number of packets to be sent in a queue.";
                  }
                  leaf revHoldTime {
                    type uint32 {
                      range "0..65535";
                    }
                    config false;
                    description
                      "Hold time of a peer.";
                  }
                  leaf revLastKeepAliveTime {
                    type yang:date-and-time;
                    config false;
                    description
                      "Last time when Keepalive packets were received from a peer.";
                  }
                  leaf negoHoldTime {
                    type uint32 {
                      range "0..65535";
                    }
                    config false;
                    description
                      "Hold time negotiated by BGP peers.";
                  }
                  leaf negoKeepAliveTime {
                    type uint32 {
                      range "0..21845";
                    }
                    config false;
                    description
                      "Keepalive time negotiated by BGP peers.";
                  }
                  leaf revUpdateCount {
                    type uint32 {
                      range "0..4294967295";
                    }
                    config false;
                    description
                      "Number of Update packets received from a peer.";
                  }
                  leaf revOpenCount {
                    type uint32 {
                      range "0..4294967295";
                    }
                    config false;
                    description
                      "Number of Open packets received from a peer.";
                  }
                  leaf revKeepAliveCount {
                    type uint32 {
                      range "0..4294967295";
                    }
                    config false;
                    description
                      "Number of Keepalive packets received from a peer.";
                  }
                  leaf revNotificationCount {
                    type uint32 {
                      range "0..4294967295";
                    }
                    config false;
                    description
                      "Number of Notification packets received from a peer.";
                  }
                  leaf revRouteRefreshCount {
                    type uint32 {
                      range "0..4294967295";
                    }
                    config false;
                    description
                      "Number of Route-Refresh packets received from a peer.";
                  }
                  leaf sentUpdateCount {
                    type uint32 {
                      range "0..4294967295";
                    }
                    config false;
                    description
                      "Number of Update packets sent to a peer.";
                  }
                  leaf sentOpenCount {
                    type uint32 {
                      range "0..4294967295";
                    }
                    config false;
                    description
                      "Number of Open packets sent to a peer.";
                  }
                  leaf sentKeepAliveCount {
                    type uint32 {
                      range "0..4294967295";
                    }
                    config false;
                    description
                      "Number of Keepalive packets sent to a peer.";
                  }
                  leaf sentNotificationCount {
                    type uint32 {
                      range "0..4294967295";
                    }
                    config false;
                    description
                      "Number of Notification packets sent to a peer.";
                  }
                  leaf sentRouteRefreshCount {
                    type uint32 {
                      range "0..4294967295";
                    }
                    config false;
                    description
                      "Number of Route-Refresh packets sent to a peer.";
                  }
                  leaf sendGRCapability {
                    type boolean;
                    config false;
                    description
                      "Whether the local end supports RR.";
                  }
                  leaf revRefreshCapability {
                    type boolean;
                    config false;
                    description
                      "Whether the peer supports RR.";
                  }
                  leaf revFourByteASCapability {
                    type boolean;
                    config false;
                    description
                      "Whether the peer supports 4-byte AS numbers.";
                  }
                  leaf revSupportMPCapability {
                    type boolean;
                    config false;
                    description
                      "Whether the peer supports MP.";
                  }
                  leaf revGRCapability {
                    type boolean;
                    config false;
                    description
                      "Whether the peer supports GR.";
                  }
                  leaf addPathRecv {
                    type string {
                      length "1..50";
                    }
                    config false;
                    description
                      "Whether the peer supports Add-Path.";
                  }
                  leaf addPathNego {
                    type string {
                      length "1..50";
                    }
                    config false;
                    description
                      "Negotiated Add-Path.";
                  }
                  leaf addPathLblRecv {
                    type string {
                      length "1..50";
                    }
                    config false;
                    description
                      "Whether the peer supports labeled Add-Path.";
                  }
                  leaf addPathLblNego {
                    type string {
                      length "1..50";
                    }
                    config false;
                    description
                      "Negotiated Label Add-Path.";
                  }
                  leaf prefRecv {
                    type uint32 {
                      range "0..4294967295";
                    }
                    config false;
                    description
                      "Number of received route prefixes.";
                  }
                  leaf activePrefRecv {
                    type uint32 {
                      range "0..4294967295";
                    }
                    config false;
                    description
                      "Number of received prefixes of active routes.";
                  }
                  leaf prefAdvertised {
                    type uint32 {
                      range "0..4294967295";
                    }
                    config false;
                    description
                      "Number of advertised route prefixes.";
                  }
                  leaf attrdiscardstr {
                    type string {
                      length "1..300";
                    }
                    config false;
                    description
                      "The attribute id discard info.";
                  }
                  leaf checkFirstAs {
                    type bgpCheckFirstAsRealState;
                    config false;
                    description
                      "Check the first AS in the AS_Path of the update messages from EBGP peers. By default, this function is enabled.";
                  }
                  leaf peerExtNhpCap {
                    type boolean;
                    config false;
                    description
                      "Peer Extended Next Hop Encoding capability";
                  }
                }
                container defOriginates {
                  when "not(../../../afType='ipv4vpnmcast' or ../../../afType='mdt' or ../../../afType='rpd' or ../../../afType='vpntarget' or ../../../afType='vpnv4flow' or ../../../afType='vpnv6flow')";
                  description
                    "List of advertised default VPNv4 routes.";
                  list defOriginate {
                    when "../../../../afType='ipv4vpn'";
                    key "configVrfName";
                    description
                      "Advertised default VPNv4 route";
                    leaf configVrfName {
                      type leafref {
                        path "/l3vpn:l3vpn/l3vpn:l3vpncomm/l3vpn:l3vpnInstances/l3vpn:l3vpnInstance/l3vpn:vrfName";
                      }
                      description
                        "VPN instance name. It uniquely identifies a VPN instance. The name is a string of case-sensitive characters.";
                    }
                  }
                }
                container rpdPolicyInfos {
                  config false;
                  description
                    "RPD policy information table.";
                  uses bgp:bgp_bgpcomm_rpdPolicyInfos_type;
                }
                container peerRpdRevRtTables {
                  config false;
                  description
                    "RPD routing tables.";
                  uses bgp:bgp_bgpcomm_peerRpdRevRtTables_type;
                }
                container peerRpdAdvRtTables {
                  config false;
                  description
                    "RPD adv routing tables.";
                  uses bgp:bgp_bgpcomm_peerRpdAdvRtTables_type;
                }
                container peerRevActRtTables {
                  config false;
                  description
                    "peerRevActRtTables.";
                  list peerRevActRtTable {
                    when "not(../../../../afType!='ipv4uni' and ../../../../afType!='ipv4multi' and ../../../../afType!='ipv4vpn' and ../../../../afType!='ipv6uni' and ../../../../afType!='ipv6vpn')";
                    key "networkPrefix prefixMask routeTypeFlag imTableId rd from pathID";
                    config false;
                    description
                      "peerRevActRtTable.";
                    leaf networkPrefix {
                      type inet:ip-address-no-zone;
                      config false;
                      description
                        "BGP route prefix.";
                    }
                    leaf prefixMask {
                      type uint8;
                      config false;
                      description
                        "Prefix mask.";
                    }
                    leaf routeTypeFlag {
                      type pub-type:bits32 {
                        ext:masklen 32;
                          ext:bit "ibgp" {
                            position 0;
                          }
                          ext:bit "ebgp" {
                            position 1;
                          }
                          ext:bit "network" {
                            position 2;
                          }
                          ext:bit "import" {
                            position 3;
                          }
                          ext:bit "auto-summary" {
                            position 4;
                          }
                          ext:bit "aggregate" {
                            position 5;
                          }
                          ext:bit "cpri" {
                            position 6;
                          }
                          ext:bit "pcri" {
                            position 7;
                          }
                          ext:bit "suppressed" {
                            position 8;
                          }
                          ext:bit "NHP-EMPTY" {
                            position 9;
                          }
                          ext:bit "NO-ADV" {
                            position 10;
                          }
                          ext:bit "local_cross" {
                            position 11;
                          }
                          ext:bit "remote_cross" {
                            position 12;
                          }
                          ext:bit "VD-BGP" {
                            position 13;
                          }
                          ext:bit "PATH_LOCAL" {
                            position 14;
                          }
                          ext:bit "PATH_GATEWAY" {
                            position 15;
                          }
                          ext:bit "policy_nopass" {
                            position 16;
                          }
                          ext:bit "supprenet" {
                            position 17;
                          }
                          ext:bit "dampened" {
                            position 18;
                          }
                          ext:bit "history" {
                            position 19;
                          }
                          ext:bit "select" {
                            position 20;
                          }
                          ext:bit "best" {
                            position 21;
                          }
                          ext:bit "backup" {
                            position 22;
                          }
                          ext:bit "attr_change" {
                            position 23;
                          }
                          ext:bit "NHLFE_CREATED" {
                            position 24;
                          }
                          ext:bit "ILM_CREATED" {
                            position 25;
                          }
                          ext:bit "NEXTHOP_CHANGE" {
                            position 26;
                          }
                          ext:bit "Invaild" {
                            position 27;
                          }
                          ext:bit "SOURCE_CHANGE" {
                            position 28;
                          }
                          ext:bit "IN_SELECTEDQ" {
                            position 29;
                          }
                          ext:bit "EXITIF_ERROR" {
                            position 30;
                          }
                          ext:bit "GROUP_HEAD" {
                            position 31;
                          }
                      }
                      config false;
                      description
                        "Route type.";
                    }
                    leaf imTableId {
                      type uint32 {
                        range "0..4294967295";
                      }
                      config false;
                      description
                        "ID of the routing table to which routes are imported.";
                    }
                    leaf rd {
                      type string {
                        length "1..22";
                      }
                      config false;
                      description
                        "Route distinguisher.";
                    }
                    leaf from {
                      type inet:ip-address-no-zone;
                      config false;
                      description
                        "Source peer that sends a route.";
                    }
                    leaf pathID {
                      type string {
                        length "1..50";
                      }
                      config false;
                      description
                        "Path ID.";
                    }
                    leaf remoteNextHopTunnelAddress {
                      type inet:ip-address-no-zone;
                      config false;
                      description
                        "The remote next hop tunnel address.";
                    }
                    leaf remoteNextHopMacAddress {
                      type pub-type:macAddress;
                      config false;
                      description
                        "The Remote next hop mac.";
                    }
                    leaf nexthop {
                      type inet:ip-address-no-zone;
                      config false;
                      description
                        "Next hop address to which packets are forwarded.";
                    }
                    leaf locPrf {
                      type uint32 {
                        range "0..4294967295";
                      }
                      config false;
                      description
                        "Local priority.The attribute is only fit for the routes from IBGP peer, not suit for which of EBGP peer.";
                    }
                    leaf prefVal {
                      type uint32 {
                        range "0..4294967295";
                      }
                      config false;
                      description
                        "Preferred value of a protocol.";
                    }
                    leaf prefrence {
                      type uint8 {
                        range "0..255";
                      }
                      config false;
                      description
                        "Priority of BGP routes.";
                    }
                    leaf pathAs {
                      type string {
                        length "1..300";
                      }
                      config false;
                      description
                        "List of the AS_Paths that packets pass through.";
                    }
                    leaf origin {
                      type bgpcommOrigin;
                      config false;
                      description
                        "Route origin.";
                    }
                    leaf med {
                      type uint32 {
                        range "0..4294967295";
                      }
                      config false;
                      description
                        "Route MED.The attribute is only fit for the routes from EBGP peer, not suit for which of IBGP peer.";
                    }
                    leaf flagString {
                      type string {
                        length "1..100";
                      }
                      config false;
                      description
                        "Route flag that contains a string of characters.";
                    }
                    leaf rtWorseReason {
                      type string {
                        length "1..50";
                      }
                      config false;
                      description
                        "Reason why a route is not selected.";
                    }
                    leaf peerString {
                      type string {
                        length "1..300";
                      }
                      config false;
                      description
                        "List of route sending peers.";
                    }
                    leaf time {
                      type uint32 {
                        range "0..4294967295";
                      }
                      config false;
                      description
                        "Time stamp of a route.";
                    }
                    leaf community {
                      type string {
                        length "1..120";
                      }
                      config false;
                      description
                        "Community attribute.";
                    }
                    leaf extCommunity {
                      type string {
                        length "1..300";
                      }
                      config false;
                      description
                        "Extended community attribute.";
                    }
                    leaf ifName {
                      type leafref {
                        path "/ifm:ifm/ifm:interfaces/ifm:interface/ifm:ifName";
                      }
                      config false;
                      description
                        "Name of the outbound interface of a route.";
                    }
                    leaf originator {
                      type inet:ip-address-no-zone;
                      config false;
                      description
                        "Router ID of the route initiator.";
                    }
                    leaf clusterList {
                      type string {
                        length "1..300";
                      }
                      config false;
                      description
                        "List of cluster IDs.";
                    }
                    leaf remoteRouteId {
                      type inet:ipv4-address-no-zone;
                      config false;
                      description
                        "Router ID of a peer.";
                    }
                    leaf relayNexthop {
                      type inet:ip-address-no-zone;
                      config false;
                      description
                        "Next hop to which a route is iterated.";
                    }
                    leaf relaytnlName {
                      type string {
                        length "1..64";
                      }
                      config false;
                      description
                        "Name of a tunnel to which a route is iterated.";
                    }
                    leaf isAtomicAggre {
                      type boolean;
                      default "false";
                      config false;
                      description
                        "Route carrying the atomic-aggregate attribute.";
                    }
                    leaf aggregatorAs {
                      type string {
                        length "1..11";
                      }
                      config false;
                      description
                        "AS number of the route summarizer.";
                    }
                    leaf aggregatorId {
                      type inet:ip-address-no-zone;
                      config false;
                      description
                        "ID of the route summarizer.";
                    }
                    leaf inLabel {
                      type uint32 {
                        range "0..4294967295";
                      }
                      config false;
                      description
                        "In-label.";
                    }
                    leaf outLabel {
                      type uint32 {
                        range "0..4294967295";
                      }
                      config false;
                      description
                        "Out-label.";
                    }
                    leaf disAttrString {
                      type string {
                        length "1..300";
                      }
                      config false;
                      description
                        "Discard the route attribute list.";
                    }
                    leaf vrfName {
                      type string {
                        length "1..31";
                      }
                      config false;
                      description
                        "Iterated Vrf .";
                    }
                    leaf remoteNextHopVni {
                      type uint32 {
                        range "0..4294967295";
                      }
                      config false;
                      description
                        "The remote next hop vni.";
                    }
                    leaf advNextHop {
                      type inet:ip-address-no-zone;
                      config false;
                      description
                        "Advertised Nexthop.";
                    }
                    leaf prefixSid {
                      type string {
                        length "1..60";
                      }
                      config false;
                      description
                        "PrefixSid attribute information of Route.";
                    }
                    leaf aigp {
                      type uint64;
                      config false;
                      description
                        "AIGP attribute information of Route.";
                    }
                    leaf attrSetString {
                      type string {
                        length "1..300";
                      }
                      config false;
                      description
                        "The attribute set information of Route.";
                    }
                  }
                }
                container peerflowRevRtTables {
                  config false;
                  description
                    "List of displayed BGP Flow Specification route information.";
                  list peerflowRevRtTable {
                    when "not(../../../../afType!='ipv6flow' and ../../../../afType!='ipv4flow')";
                    key "reIndex isLocalRoute localRouteName from";
                    config false;
                    description
                      "Information about BGP Flow Specification routes.";
                    leaf reIndex {
                      type uint32 {
                        range "1..4294967295";
                      }
                      config false;
                      description
                        "BGP Flow Specification route index. The value is an integer ranging from 1 to 4294967295.";
                    }
                    leaf isLocalRoute {
                      type boolean;
                      config false;
                      description
                        "The BGP Flow Specification route is a local route.";
                    }
                    leaf localRouteName {
                      type string {
                        length "1..30";
                      }
                      config false;
                      description
                        "Name of a local BGP Flow Specification route.";
                    }
                    leaf from {
                      type inet:ip-address-no-zone;
                      config false;
                      description
                        "Source peer that sends a route.";
                    }
                    leaf routeTypeFlag {
                      type pub-type:bits32 {
                        ext:masklen 32;
                          ext:bit "ibgp" {
                            position 0;
                          }
                          ext:bit "ebgp" {
                            position 1;
                          }
                          ext:bit "network" {
                            position 2;
                          }
                          ext:bit "import" {
                            position 3;
                          }
                          ext:bit "auto-summary" {
                            position 4;
                          }
                          ext:bit "aggregate" {
                            position 5;
                          }
                          ext:bit "cpri" {
                            position 6;
                          }
                          ext:bit "pcri" {
                            position 7;
                          }
                          ext:bit "suppressed" {
                            position 8;
                          }
                          ext:bit "NHP-EMPTY" {
                            position 9;
                          }
                          ext:bit "NO-ADV" {
                            position 10;
                          }
                          ext:bit "local_cross" {
                            position 11;
                          }
                          ext:bit "remote_cross" {
                            position 12;
                          }
                          ext:bit "VD-BGP" {
                            position 13;
                          }
                          ext:bit "PATH_LOCAL" {
                            position 14;
                          }
                          ext:bit "PATH_GATEWAY" {
                            position 15;
                          }
                          ext:bit "policy_nopass" {
                            position 16;
                          }
                          ext:bit "supprenet" {
                            position 17;
                          }
                          ext:bit "dampened" {
                            position 18;
                          }
                          ext:bit "history" {
                            position 19;
                          }
                          ext:bit "select" {
                            position 20;
                          }
                          ext:bit "best" {
                            position 21;
                          }
                          ext:bit "backup" {
                            position 22;
                          }
                          ext:bit "attr_change" {
                            position 23;
                          }
                          ext:bit "NHLFE_CREATED" {
                            position 24;
                          }
                          ext:bit "ILM_CREATED" {
                            position 25;
                          }
                          ext:bit "NEXTHOP_CHANGE" {
                            position 26;
                          }
                          ext:bit "Invaild" {
                            position 27;
                          }
                          ext:bit "SOURCE_CHANGE" {
                            position 28;
                          }
                          ext:bit "IN_SELECTEDQ" {
                            position 29;
                          }
                          ext:bit "EXITIF_ERROR" {
                            position 30;
                          }
                          ext:bit "GROUP_HEAD" {
                            position 31;
                          }
                      }
                      config false;
                      description
                        "Route Type.";
                    }
                    leaf peerRouterId {
                      type inet:ipv4-address-no-zone;
                      config false;
                      description
                        "Router ID of a peer.";
                    }
                    leaf order {
                      type uint32 {
                        range "0..4294967295";
                      }
                      config false;
                      description
                        "Filtering rule delivery order.";
                    }
                    leaf isApplyDeny {
                      type boolean;
                      config false;
                      description
                        "Deny the traffic that matches the traffic policy.";
                    }
                    leaf isApplySample {
                      type boolean;
                      config false;
                      description
                        "Enable Apply Sample.";
                    }
                    leaf isApplyNextTerm {
                      type boolean;
                      config false;
                      description
                        "Enable Apply Next-Term.";
                    }
                    leaf remarkDscp {
                      type string {
                        length "1..50";
                      }
                      config false;
                      description
                        "Filtering rules to re-mark the DSCP value.";
                    }
                    leaf trafficRate {
                      type string {
                        length "1..50";
                      }
                      config false;
                      description
                        "Traffic rate rule.";
                    }
                    leaf redirectIP {
                      type string {
                        length "9..17";
                      }
                      config false;
                      description
                        "Redirect IP of a BGP Flow Specification route.";
                    }
                    leaf relayTnlName {
                      type string {
                        length "1..64";
                      }
                      config false;
                      description
                        "Flow Route Redirect Relay Tunnel.";
                    }
                    leaf validationResult {
                      type pub-type:bits8 {
                        ext:masklen 7;
                          ext:bit "notenable" {
                            position 0;
                          }
                          ext:bit "checking" {
                            position 1;
                          }
                          ext:bit "accept" {
                            position 2;
                          }
                          ext:bit "discard" {
                            position 3;
                          }
                      }
                      config false;
                      description
                        "EBGP Redirect IP Validate Result.";
                    }
                    leaf vpnTarget {
                      type string {
                        length "1..22";
                      }
                      config false;
                      description
                        "VPN target of a BGP Flow Specification route.";
                    }
                    leaf isReflectClient {
                      type boolean;
                      config false;
                      description
                        "The device is an RR.";
                    }
                    leaf dscp {
                      type string {
                        length "1..50";
                      }
                      config false;
                      description
                        "DSCP rule.";
                    }
                    leaf destinationPrefix {
                      type inet:ip-address-no-zone;
                      config false;
                      description
                        "Destination prefix-based filtering rule.";
                    }
                    leaf desPrefixMaskLen {
                      type uint8 {
                        range "0..128";
                      }
                      config false;
                      description
                        "Destination prefix mask length.";
                    }
                    leaf sourcePrefix {
                      type inet:ip-address-no-zone;
                      config false;
                      description
                        "Source prefix-based filtering rule.";
                    }
                    leaf srcPrefixMaskLen {
                      type uint8 {
                        range "0..128";
                      }
                      config false;
                      description
                        "Source Prefix mask length.";
                    }
                    leaf protocol {
                      type string {
                        length "1..50";
                      }
                      config false;
                      description
                        "IP protocol-based filtering rule for BGP Flow Specification routes.";
                    }
                    leaf port {
                      type string {
                        length "1..50";
                      }
                      config false;
                      description
                        "Port number-based filtering rule.";
                    }
                    leaf destinationPort {
                      type string {
                        length "1..50";
                      }
                      config false;
                      description
                        "Destination port number-based filtering rule.";
                    }
                    leaf sourcePort {
                      type string {
                        length "1..50";
                      }
                      config false;
                      description
                        "Source port number-based filtering rule.";
                    }
                    leaf icmpType {
                      type string {
                        length "1..50";
                      }
                      config false;
                      description
                        "ICMP type-based filtering rule.";
                    }
                    leaf icmpCode {
                      type string {
                        length "1..50";
                      }
                      config false;
                      description
                        "ICMP code-based filtering rule.";
                    }
                    leaf tcpFlags {
                      type string {
                        length "1..50";
                      }
                      config false;
                      description
                        "TCP Flag-based filtering rule.";
                    }
                    leaf packetlength {
                      type string {
                        length "1..50";
                      }
                      config false;
                      description
                        "Packet length-based filtering rule.";
                    }
                    leaf fragmentType {
                      type string {
                        length "1..50";
                      }
                      config false;
                      description
                        "Fragment type-based filtering rule.";
                    }
                    leaf isUnkownRule {
                      type boolean;
                      config false;
                      description
                        "Unknown rule.";
                    }
                    leaf med {
                      type uint32 {
                        range "0..4294967295";
                      }
                      config false;
                      description
                        "MED.The attribute is only fit for the routes from EBGP peer, not suit for which of IBGP peer.";
                    }
                    leaf prefVal {
                      type uint32 {
                        range "0..4294967295";
                      }
                      config false;
                      description
                        "PrefVal.";
                    }
                    leaf localPrefrence {
                      type uint8 {
                        range "0..255";
                      }
                      config false;
                      description
                        "Local-Preference.";
                    }
                    leaf origin {
                      type bgpcommOrigin;
                      config false;
                      description
                        "Route origin.";
                    }
                    leaf originator {
                      type inet:ipv4-address-no-zone;
                      config false;
                      description
                        "Router ID of the route initiator.";
                    }
                    leaf routeDuration {
                      type uint32 {
                        range "0..4294967295";
                      }
                      config false;
                      description
                        "Route duration.";
                    }
                    leaf flagString {
                      type string {
                        length "1..100";
                      }
                      config false;
                      description
                        "Route flag that contains a string of characters.";
                    }
                    leaf community {
                      type string {
                        length "1..120";
                      }
                      config false;
                      description
                        "Community attribute of a BGP Flow Specification route.";
                    }
                    leaf extCommunity {
                      type string {
                        length "1..300";
                      }
                      config false;
                      description
                        "Extended community attribute of a BGP Flow Specification route.";
                    }
                    leaf clusterlist {
                      type string {
                        length "1..300";
                      }
                      config false;
                      description
                        "Cluster list of a BGP Flow Specification route.";
                    }
                    leaf pathAs {
                      type string {
                        length "1..300";
                      }
                      config false;
                      description
                        "List of the AS_Paths that packets pass through.";
                    }
                    leaf rtWorseReason {
                      type string {
                        length "1..50";
                      }
                      config false;
                      description
                        "Reason why a route is not selected.";
                    }
                    leaf peerString {
                      type string {
                        length "1..300";
                      }
                      config false;
                      description
                        "List of route sending peers.";
                    }
                    leaf ruleNumber {
                      type uint64;
                      config false;
                      description
                        "Number of rules for BGP Flow Specification routes.";
                    }
                    leaf matchPackets {
                      type uint64;
                      config false;
                      description
                        "Number of matched packets.";
                    }
                    leaf matchBytes {
                      type uint64;
                      config false;
                      description
                        "Number of matched bytes.";
                    }
                    leaf matchPacketPer30Sec {
                      type uint64;
                      config false;
                      description
                        "Number of matched packets each 30 seconds.";
                    }
                    leaf matchBytePer30Sec {
                      type uint64;
                      config false;
                      description
                        "Number of matched bytes each 30 seconds.";
                    }
                    leaf trafActFlag {
                      type pub-type:bits8 {
                        ext:masklen 7;
                          ext:bit "route-policy-distribute" {
                            position 1;
                          }
                      }
                      config false;
                      description
                        "Traffic action flag.";
                    }
                    leaf invalidReason {
                      type string {
                        length "0..250";
                      }
                      config false;
                      description
                        "Why a route cannot be delivered to the FIB.";
                    }
                    container wideCommunitys {
                      config false;
                      description
                        "Wide-community information.";
                      list wideCommunity {
                        key "index type flag hopCount";
                        config false;
                        description
                          "Wide-community information.";
                        leaf index {
                          type uint32;
                          config false;
                          description
                            "Index.";
                        }
                        leaf type {
                          type uint32;
                          config false;
                          description
                            "Type.";
                        }
                        leaf flag {
                          type pub-type:hexBinary;
                          config false;
                          description
                            "Flag.";
                        }
                        leaf hopCount {
                          type uint32;
                          config false;
                          description
                            "Hop count.";
                        }
                        leaf communityValue {
                          type pub-type:hexBinary;
                          config false;
                          description
                            "Community value.";
                        }
                        leaf sourceAs {
                          type asNumberValidate;
                          config false;
                          description
                            "Source AS.";
                        }
                        leaf contextAs {
                          type asNumberValidate;
                          config false;
                          description
                            "Context AS.";
                        }
                        leaf param {
                          type string {
                            length "0..2030";
                          }
                          config false;
                          description
                            "Parameter.";
                        }
                      }
                    }
                    container redirectIpRelays {
                      config false;
                      description
                        "Redirection IP information.";
                      list redirectIpRelay {
                        key "redirectIp";
                        config false;
                        description
                          "Redirection IP information.";
                        leaf redirectIp {
                          type inet:ipv4-address-no-zone;
                          config false;
                          description
                            "Redirection IP address.";
                        }
                        leaf redirectOpt {
                          type uint32;
                          config false;
                          description
                            "Operation code.";
                        }
                        leaf redirectResult {
                          type string {
                            length "1..100";
                          }
                          config false;
                          description
                            "Iteration result.";
                        }
                        leaf relayNextHop {
                          type inet:ipv4-address-no-zone;
                          config false;
                          description
                            "IP iteration next hop.";
                        }
                        leaf outIfName {
                          type pub-type:ifName;
                          config false;
                          description
                            "IP iteration outbound interface.";
                        }
                        leaf relayTnlNextHop {
                          type inet:ipv4-address-no-zone;
                          config false;
                          description
                            "Tunnel iteration next hop.";
                        }
                        leaf relayTnlOutIfName {
                          type pub-type:ifName;
                          config false;
                          description
                            "Tunnel iteration outbund interface.";
                        }
                      }
                    }
                    container flowInfGrpStats {
                      config false;
                      description
                        "Statistics of the BGP Flow Specification route with the specified reIndex and flow interface group ID.";
                      list flowInfGrpStat {
                        key "flowIfGrpIndex";
                        config false;
                        description
                          "Statistic of the BGP Flow Specification route with the specified reIndex and flow interface group ID.";
                        leaf flowIfGrpIndex {
                          type uint32 {
                            range "0..16383";
                          }
                          config false;
                          description
                            "Flow interface group ID.";
                        }
                        leaf ruleNumber {
                          type uint64;
                          config false;
                          description
                            "Number of rules for BGP Flow Specification routes.";
                        }
                        leaf matchPackets {
                          type uint64;
                          config false;
                          description
                            "Number of matched packets.";
                        }
                        leaf matchBytes {
                          type uint64;
                          config false;
                          description
                            "Number of matched bytes.";
                        }
                        leaf matchPacketPer30Sec {
                          type uint64;
                          config false;
                          description
                            "Number of matched packets each 30 seconds.";
                        }
                        leaf matchBytePer30Sec {
                          type uint64;
                          config false;
                          description
                            "Number of matched bytes each 30 seconds.";
                        }
                      }
                    }
                  }
                }
                container peerflowAdvRtTables {
                  config false;
                  description
                    "List of displayed BGP Flow Specification route information.";
                  list peerflowAdvRtTable {
                    when "not(../../../../afType!='ipv6flow' and ../../../../afType!='ipv4flow')";
                    key "reIndex isLocalRoute localRouteName from";
                    config false;
                    description
                      "Information about BGP Flow Specification routes.";
                    leaf reIndex {
                      type uint32 {
                        range "1..4294967295";
                      }
                      config false;
                      description
                        "BGP Flow Specification route index. The value is an integer ranging from 1 to 4294967295.";
                    }
                    leaf isLocalRoute {
                      type boolean;
                      config false;
                      description
                        "The BGP Flow Specification route is a local route.";
                    }
                    leaf localRouteName {
                      type string {
                        length "1..30";
                      }
                      config false;
                      description
                        "Name of a local BGP Flow Specification route.";
                    }
                    leaf from {
                      type inet:ip-address-no-zone;
                      config false;
                      description
                        "Source peer that sends a route.";
                    }
                    leaf routeTypeFlag {
                      type pub-type:bits32 {
                        ext:masklen 32;
                          ext:bit "ibgp" {
                            position 0;
                          }
                          ext:bit "ebgp" {
                            position 1;
                          }
                          ext:bit "network" {
                            position 2;
                          }
                          ext:bit "import" {
                            position 3;
                          }
                          ext:bit "auto-summary" {
                            position 4;
                          }
                          ext:bit "aggregate" {
                            position 5;
                          }
                          ext:bit "cpri" {
                            position 6;
                          }
                          ext:bit "pcri" {
                            position 7;
                          }
                          ext:bit "suppressed" {
                            position 8;
                          }
                          ext:bit "NHP-EMPTY" {
                            position 9;
                          }
                          ext:bit "NO-ADV" {
                            position 10;
                          }
                          ext:bit "local_cross" {
                            position 11;
                          }
                          ext:bit "remote_cross" {
                            position 12;
                          }
                          ext:bit "VD-BGP" {
                            position 13;
                          }
                          ext:bit "PATH_LOCAL" {
                            position 14;
                          }
                          ext:bit "PATH_GATEWAY" {
                            position 15;
                          }
                          ext:bit "policy_nopass" {
                            position 16;
                          }
                          ext:bit "supprenet" {
                            position 17;
                          }
                          ext:bit "dampened" {
                            position 18;
                          }
                          ext:bit "history" {
                            position 19;
                          }
                          ext:bit "select" {
                            position 20;
                          }
                          ext:bit "best" {
                            position 21;
                          }
                          ext:bit "backup" {
                            position 22;
                          }
                          ext:bit "attr_change" {
                            position 23;
                          }
                          ext:bit "NHLFE_CREATED" {
                            position 24;
                          }
                          ext:bit "ILM_CREATED" {
                            position 25;
                          }
                          ext:bit "NEXTHOP_CHANGE" {
                            position 26;
                          }
                          ext:bit "Invaild" {
                            position 27;
                          }
                          ext:bit "SOURCE_CHANGE" {
                            position 28;
                          }
                          ext:bit "IN_SELECTEDQ" {
                            position 29;
                          }
                          ext:bit "EXITIF_ERROR" {
                            position 30;
                          }
                          ext:bit "GROUP_HEAD" {
                            position 31;
                          }
                      }
                      config false;
                      description
                        "Route Type.";
                    }
                    leaf peerRouterId {
                      type inet:ipv4-address-no-zone;
                      config false;
                      description
                        "Router ID of a peer.";
                    }
                    leaf order {
                      type uint32 {
                        range "0..4294967295";
                      }
                      config false;
                      description
                        "Filtering rule delivery order.";
                    }
                    leaf isApplyDeny {
                      type boolean;
                      config false;
                      description
                        "Deny the traffic that matches the traffic policy.";
                    }
                    leaf isApplySample {
                      type boolean;
                      config false;
                      description
                        "Enable Apply Sample.";
                    }
                    leaf isApplyNextTerm {
                      type boolean;
                      config false;
                      description
                        "Enable Apply Next-Term.";
                    }
                    leaf remarkDscp {
                      type string {
                        length "1..50";
                      }
                      config false;
                      description
                        "Filtering rules to re-mark the DSCP value.";
                    }
                    leaf trafficRate {
                      type string {
                        length "1..50";
                      }
                      config false;
                      description
                        "Traffic rate rule.";
                    }
                    leaf redirectIP {
                      type string {
                        length "9..17";
                      }
                      config false;
                      description
                        "Redirect IP of a BGP Flow Specification route.";
                    }
                    leaf relayTnlName {
                      type string {
                        length "1..64";
                      }
                      config false;
                      description
                        "Flow Route Redirect Relay Tunnel.";
                    }
                    leaf validationResult {
                      type pub-type:bits8 {
                        ext:masklen 7;
                          ext:bit "notenable" {
                            position 0;
                          }
                          ext:bit "checking" {
                            position 1;
                          }
                          ext:bit "accept" {
                            position 2;
                          }
                          ext:bit "discard" {
                            position 3;
                          }
                      }
                      config false;
                      description
                        "EBGP Redirect IP Validate Result.";
                    }
                    leaf vpnTarget {
                      type string {
                        length "1..22";
                      }
                      config false;
                      description
                        "VPN target of a BGP Flow Specification route.";
                    }
                    leaf isReflectClient {
                      type boolean;
                      config false;
                      description
                        "The device is an RR.";
                    }
                    leaf dscp {
                      type string {
                        length "1..50";
                      }
                      config false;
                      description
                        "DSCP rule.";
                    }
                    leaf destinationPrefix {
                      type inet:ip-address-no-zone;
                      config false;
                      description
                        "Destination prefix-based filtering rule.";
                    }
                    leaf desPrefixMaskLen {
                      type uint8 {
                        range "0..128";
                      }
                      config false;
                      description
                        "Destination prefix mask length.";
                    }
                    leaf sourcePrefix {
                      type inet:ip-address-no-zone;
                      config false;
                      description
                        "Source prefix-based filtering rule.";
                    }
                    leaf srcPrefixMaskLen {
                      type uint8 {
                        range "0..128";
                      }
                      config false;
                      description
                        "Source Prefix mask length.";
                    }
                    leaf protocol {
                      type string {
                        length "1..50";
                      }
                      config false;
                      description
                        "IP protocol-based filtering rule for BGP Flow Specification routes.";
                    }
                    leaf port {
                      type string {
                        length "1..50";
                      }
                      config false;
                      description
                        "Port number-based filtering rule.";
                    }
                    leaf destinationPort {
                      type string {
                        length "1..50";
                      }
                      config false;
                      description
                        "Destination port number-based filtering rule.";
                    }
                    leaf sourcePort {
                      type string {
                        length "1..50";
                      }
                      config false;
                      description
                        "Source port number-based filtering rule.";
                    }
                    leaf icmpType {
                      type string {
                        length "1..50";
                      }
                      config false;
                      description
                        "ICMP type-based filtering rule.";
                    }
                    leaf icmpCode {
                      type string {
                        length "1..50";
                      }
                      config false;
                      description
                        "ICMP code-based filtering rule.";
                    }
                    leaf tcpFlags {
                      type string {
                        length "1..50";
                      }
                      config false;
                      description
                        "TCP Flag-based filtering rule.";
                    }
                    leaf packetlength {
                      type string {
                        length "1..50";
                      }
                      config false;
                      description
                        "Packet length-based filtering rule.";
                    }
                    leaf fragmentType {
                      type string {
                        length "1..50";
                      }
                      config false;
                      description
                        "Fragment type-based filtering rule.";
                    }
                    leaf isUnkownRule {
                      type boolean;
                      config false;
                      description
                        "Unknown rule.";
                    }
                    leaf med {
                      type uint32 {
                        range "0..4294967295";
                      }
                      config false;
                      description
                        "MED.The attribute is only fit for the routes from EBGP peer, not suit for which of IBGP peer.";
                    }
                    leaf prefVal {
                      type uint32 {
                        range "0..4294967295";
                      }
                      config false;
                      description
                        "PrefVal.";
                    }
                    leaf localPrefrence {
                      type uint8 {
                        range "0..255";
                      }
                      config false;
                      description
                        "Local-Preference.";
                    }
                    leaf origin {
                      type bgpcommOrigin;
                      config false;
                      description
                        "Route origin.";
                    }
                    leaf originator {
                      type inet:ipv4-address-no-zone;
                      config false;
                      description
                        "Router ID of the route initiator.";
                    }
                    leaf routeDuration {
                      type uint32 {
                        range "0..4294967295";
                      }
                      config false;
                      description
                        "Route duration.";
                    }
                    leaf flagString {
                      type string {
                        length "1..100";
                      }
                      config false;
                      description
                        "Route flag that contains a string of characters.";
                    }
                    leaf community {
                      type string {
                        length "1..120";
                      }
                      config false;
                      description
                        "Community attribute of a BGP Flow Specification route.";
                    }
                    leaf extCommunity {
                      type string {
                        length "1..300";
                      }
                      config false;
                      description
                        "Extended community attribute of a BGP Flow Specification route.";
                    }
                    leaf clusterlist {
                      type string {
                        length "1..300";
                      }
                      config false;
                      description
                        "Cluster list of a BGP Flow Specification route.";
                    }
                    leaf pathAs {
                      type string {
                        length "1..300";
                      }
                      config false;
                      description
                        "List of the AS_Paths that packets pass through.";
                    }
                    leaf rtWorseReason {
                      type string {
                        length "1..50";
                      }
                      config false;
                      description
                        "Reason why a route is not selected.";
                    }
                    leaf peerString {
                      type string {
                        length "1..300";
                      }
                      config false;
                      description
                        "List of route sending peers.";
                    }
                    leaf ruleNumber {
                      type uint64;
                      config false;
                      description
                        "Number of rules for BGP Flow Specification routes.";
                    }
                    leaf matchPackets {
                      type uint64;
                      config false;
                      description
                        "Number of matched packets.";
                    }
                    leaf matchBytes {
                      type uint64;
                      config false;
                      description
                        "Number of matched bytes.";
                    }
                    leaf matchPacketPer30Sec {
                      type uint64;
                      config false;
                      description
                        "Number of matched packets each 30 seconds.";
                    }
                    leaf matchBytePer30Sec {
                      type uint64;
                      config false;
                      description
                        "Number of matched bytes each 30 seconds.";
                    }
                    leaf trafActFlag {
                      type pub-type:bits8 {
                        ext:masklen 7;
                          ext:bit "route-policy-distribute" {
                            position 1;
                          }
                      }
                      config false;
                      description
                        "Traffic action flag.";
                    }
                    leaf invalidReason {
                      type string {
                        length "0..250";
                      }
                      config false;
                      description
                        "Why a route cannot be delivered to the FIB.";
                    }
                    container wideCommunitys {
                      config false;
                      description
                        "Wide-community information.";
                      list wideCommunity {
                        key "index type flag hopCount";
                        config false;
                        description
                          "Wide-community information.";
                        leaf index {
                          type uint32;
                          config false;
                          description
                            "Index.";
                        }
                        leaf type {
                          type uint32;
                          config false;
                          description
                            "Type.";
                        }
                        leaf flag {
                          type pub-type:hexBinary;
                          config false;
                          description
                            "Flag.";
                        }
                        leaf hopCount {
                          type uint32;
                          config false;
                          description
                            "Hop count.";
                        }
                        leaf communityValue {
                          type pub-type:hexBinary;
                          config false;
                          description
                            "Community value.";
                        }
                        leaf sourceAs {
                          type asNumberValidate;
                          config false;
                          description
                            "Source AS.";
                        }
                        leaf contextAs {
                          type asNumberValidate;
                          config false;
                          description
                            "Context AS.";
                        }
                        leaf param {
                          type string {
                            length "0..2030";
                          }
                          config false;
                          description
                            "Parameter.";
                        }
                      }
                    }
                    container redirectIpRelays {
                      config false;
                      description
                        "Redirection IP information.";
                      list redirectIpRelay {
                        key "redirectIp";
                        config false;
                        description
                          "Redirection IP information.";
                        leaf redirectIp {
                          type inet:ipv4-address-no-zone;
                          config false;
                          description
                            "Redirection IP address.";
                        }
                        leaf redirectOpt {
                          type uint32;
                          config false;
                          description
                            "Operation code.";
                        }
                        leaf redirectResult {
                          type string {
                            length "1..100";
                          }
                          config false;
                          description
                            "Iteration result.";
                        }
                        leaf relayNextHop {
                          type inet:ipv4-address-no-zone;
                          config false;
                          description
                            "IP iteration next hop.";
                        }
                        leaf outIfName {
                          type pub-type:ifName;
                          config false;
                          description
                            "IP iteration outbound interface.";
                        }
                        leaf relayTnlNextHop {
                          type inet:ipv4-address-no-zone;
                          config false;
                          description
                            "Tunnel iteration next hop.";
                        }
                        leaf relayTnlOutIfName {
                          type pub-type:ifName;
                          config false;
                          description
                            "Tunnel iteration outbund interface.";
                        }
                      }
                    }
                    container flowInfGrpStats {
                      config false;
                      description
                        "Statistics of the BGP Flow Specification route with the specified reIndex and flow interface group ID.";
                      list flowInfGrpStat {
                        key "flowIfGrpIndex";
                        config false;
                        description
                          "Statistic of the BGP Flow Specification route with the specified reIndex and flow interface group ID.";
                        leaf flowIfGrpIndex {
                          type uint32 {
                            range "0..16383";
                          }
                          config false;
                          description
                            "Flow interface group ID.";
                        }
                        leaf ruleNumber {
                          type uint64;
                          config false;
                          description
                            "Number of rules for BGP Flow Specification routes.";
                        }
                        leaf matchPackets {
                          type uint64;
                          config false;
                          description
                            "Number of matched packets.";
                        }
                        leaf matchBytes {
                          type uint64;
                          config false;
                          description
                            "Number of matched bytes.";
                        }
                        leaf matchPacketPer30Sec {
                          type uint64;
                          config false;
                          description
                            "Number of matched packets each 30 seconds.";
                        }
                        leaf matchBytePer30Sec {
                          type uint64;
                          config false;
                          description
                            "Number of matched bytes each 30 seconds.";
                        }
                      }
                    }
                  }
                }
                container peerflowRevActRtTables {
                  config false;
                  description
                    "List of displayed BGP Flow Specification Active route information.";
                  list peerflowRevActRtTable {
                    when "not(../../../../afType!='ipv6flow' and ../../../../afType!='ipv4flow')";
                    key "reIndex isLocalRoute localRouteName from";
                    config false;
                    description
                      "Information about BGP Flow Specification Active routes.";
                    leaf reIndex {
                      type uint32 {
                        range "1..4294967295";
                      }
                      config false;
                      description
                        "BGP Flow Specification route index. The value is an integer ranging from 1 to 4294967295.";
                    }
                    leaf isLocalRoute {
                      type boolean;
                      config false;
                      description
                        "The BGP Flow Specification route is a local route.";
                    }
                    leaf localRouteName {
                      type string {
                        length "1..30";
                      }
                      config false;
                      description
                        "Name of a local BGP Flow Specification route.";
                    }
                    leaf from {
                      type inet:ip-address-no-zone;
                      config false;
                      description
                        "Source peer that sends a route.";
                    }
                    leaf routeTypeFlag {
                      type pub-type:bits32 {
                        ext:masklen 32;
                          ext:bit "ibgp" {
                            position 0;
                          }
                          ext:bit "ebgp" {
                            position 1;
                          }
                          ext:bit "network" {
                            position 2;
                          }
                          ext:bit "import" {
                            position 3;
                          }
                          ext:bit "auto-summary" {
                            position 4;
                          }
                          ext:bit "aggregate" {
                            position 5;
                          }
                          ext:bit "cpri" {
                            position 6;
                          }
                          ext:bit "pcri" {
                            position 7;
                          }
                          ext:bit "suppressed" {
                            position 8;
                          }
                          ext:bit "NHP-EMPTY" {
                            position 9;
                          }
                          ext:bit "NO-ADV" {
                            position 10;
                          }
                          ext:bit "local_cross" {
                            position 11;
                          }
                          ext:bit "remote_cross" {
                            position 12;
                          }
                          ext:bit "VD-BGP" {
                            position 13;
                          }
                          ext:bit "PATH_LOCAL" {
                            position 14;
                          }
                          ext:bit "PATH_GATEWAY" {
                            position 15;
                          }
                          ext:bit "policy_nopass" {
                            position 16;
                          }
                          ext:bit "supprenet" {
                            position 17;
                          }
                          ext:bit "dampened" {
                            position 18;
                          }
                          ext:bit "history" {
                            position 19;
                          }
                          ext:bit "select" {
                            position 20;
                          }
                          ext:bit "best" {
                            position 21;
                          }
                          ext:bit "backup" {
                            position 22;
                          }
                          ext:bit "attr_change" {
                            position 23;
                          }
                          ext:bit "NHLFE_CREATED" {
                            position 24;
                          }
                          ext:bit "ILM_CREATED" {
                            position 25;
                          }
                          ext:bit "NEXTHOP_CHANGE" {
                            position 26;
                          }
                          ext:bit "Invaild" {
                            position 27;
                          }
                          ext:bit "SOURCE_CHANGE" {
                            position 28;
                          }
                          ext:bit "IN_SELECTEDQ" {
                            position 29;
                          }
                          ext:bit "EXITIF_ERROR" {
                            position 30;
                          }
                          ext:bit "GROUP_HEAD" {
                            position 31;
                          }
                      }
                      config false;
                      description
                        "Route Type.";
                    }
                    leaf peerRouterId {
                      type inet:ipv4-address-no-zone;
                      config false;
                      description
                        "Router ID of a peer.";
                    }
                    leaf order {
                      type uint32 {
                        range "0..4294967295";
                      }
                      config false;
                      description
                        "Filtering rule delivery order.";
                    }
                    leaf isApplyDeny {
                      type boolean;
                      config false;
                      description
                        "Deny the traffic that matches the traffic policy.";
                    }
                    leaf isApplySample {
                      type boolean;
                      config false;
                      description
                        "Enable Apply Sample.";
                    }
                    leaf isApplyNextTerm {
                      type boolean;
                      config false;
                      description
                        "Enable Apply Next-Term.";
                    }
                    leaf remarkDscp {
                      type string {
                        length "1..50";
                      }
                      config false;
                      description
                        "Filtering rules to re-mark the DSCP value.";
                    }
                    leaf trafficRate {
                      type string {
                        length "1..50";
                      }
                      config false;
                      description
                        "Traffic rate rule.";
                    }
                    leaf redirectIP {
                      type string {
                        length "9..17";
                      }
                      config false;
                      description
                        "Redirect IP of a BGP Flow Specification route.";
                    }
                    leaf relayTnlName {
                      type string {
                        length "1..64";
                      }
                      config false;
                      description
                        "Flow Route Redirect Relay Tunnel.";
                    }
                    leaf validationResult {
                      type pub-type:bits8 {
                        ext:masklen 7;
                          ext:bit "notenable" {
                            position 0;
                          }
                          ext:bit "checking" {
                            position 1;
                          }
                          ext:bit "accept" {
                            position 2;
                          }
                          ext:bit "discard" {
                            position 3;
                          }
                      }
                      config false;
                      description
                        "EBGP Redirect IP Validate Result.";
                    }
                    leaf vpnTarget {
                      type string {
                        length "1..22";
                      }
                      config false;
                      description
                        "VPN target of a BGP Flow Specification route.";
                    }
                    leaf isReflectClient {
                      type boolean;
                      config false;
                      description
                        "The device is an RR.";
                    }
                    leaf dscp {
                      type string {
                        length "1..50";
                      }
                      config false;
                      description
                        "DSCP rule.";
                    }
                    leaf destinationPrefix {
                      type inet:ip-address-no-zone;
                      config false;
                      description
                        "Destination prefix-based filtering rule.";
                    }
                    leaf desPrefixMaskLen {
                      type uint8 {
                        range "0..128";
                      }
                      config false;
                      description
                        "Destination prefix mask length.";
                    }
                    leaf sourcePrefix {
                      type inet:ip-address-no-zone;
                      config false;
                      description
                        "Source prefix-based filtering rule.";
                    }
                    leaf srcPrefixMaskLen {
                      type uint8 {
                        range "0..128";
                      }
                      config false;
                      description
                        "Source Prefix mask length.";
                    }
                    leaf protocol {
                      type string {
                        length "1..50";
                      }
                      config false;
                      description
                        "IP protocol-based filtering rule for BGP Flow Specification routes.";
                    }
                    leaf port {
                      type string {
                        length "1..50";
                      }
                      config false;
                      description
                        "Port number-based filtering rule.";
                    }
                    leaf destinationPort {
                      type string {
                        length "1..50";
                      }
                      config false;
                      description
                        "Destination port number-based filtering rule.";
                    }
                    leaf sourcePort {
                      type string {
                        length "1..50";
                      }
                      config false;
                      description
                        "Source port number-based filtering rule.";
                    }
                    leaf icmpType {
                      type string {
                        length "1..50";
                      }
                      config false;
                      description
                        "ICMP type-based filtering rule.";
                    }
                    leaf icmpCode {
                      type string {
                        length "1..50";
                      }
                      config false;
                      description
                        "ICMP code-based filtering rule.";
                    }
                    leaf tcpFlags {
                      type string {
                        length "1..50";
                      }
                      config false;
                      description
                        "TCP Flag-based filtering rule.";
                    }
                    leaf packetlength {
                      type string {
                        length "1..50";
                      }
                      config false;
                      description
                        "Packet length-based filtering rule.";
                    }
                    leaf fragmentType {
                      type string {
                        length "1..50";
                      }
                      config false;
                      description
                        "Fragment type-based filtering rule.";
                    }
                    leaf isUnkownRule {
                      type boolean;
                      config false;
                      description
                        "Unknown rule.";
                    }
                    leaf med {
                      type uint32 {
                        range "0..4294967295";
                      }
                      config false;
                      description
                        "MED.The attribute is only fit for the routes from EBGP peer, not suit for which of IBGP peer.";
                    }
                    leaf prefVal {
                      type uint32 {
                        range "0..4294967295";
                      }
                      config false;
                      description
                        "PrefVal.";
                    }
                    leaf localPrefrence {
                      type uint8 {
                        range "0..255";
                      }
                      config false;
                      description
                        "Local-Preference.";
                    }
                    leaf origin {
                      type bgpcommOrigin;
                      config false;
                      description
                        "Route origin.";
                    }
                    leaf originator {
                      type inet:ipv4-address-no-zone;
                      config false;
                      description
                        "Router ID of the route initiator.";
                    }
                    leaf routeDuration {
                      type uint32 {
                        range "0..4294967295";
                      }
                      config false;
                      description
                        "Route duration.";
                    }
                    leaf flagString {
                      type string {
                        length "1..100";
                      }
                      config false;
                      description
                        "Route flag that contains a string of characters.";
                    }
                    leaf community {
                      type string {
                        length "1..120";
                      }
                      config false;
                      description
                        "Community attribute of a BGP Flow Specification route.";
                    }
                    leaf extCommunity {
                      type string {
                        length "1..300";
                      }
                      config false;
                      description
                        "Extended community attribute of a BGP Flow Specification route.";
                    }
                    leaf clusterlist {
                      type string {
                        length "1..300";
                      }
                      config false;
                      description
                        "Cluster list of a BGP Flow Specification route.";
                    }
                    leaf pathAs {
                      type string {
                        length "1..300";
                      }
                      config false;
                      description
                        "List of the AS_Paths that packets pass through.";
                    }
                    leaf rtWorseReason {
                      type string {
                        length "1..50";
                      }
                      config false;
                      description
                        "Reason why a route is not selected.";
                    }
                    leaf peerString {
                      type string {
                        length "1..300";
                      }
                      config false;
                      description
                        "List of route sending peers.";
                    }
                    leaf ruleNumber {
                      type uint64;
                      config false;
                      description
                        "Number of rules for BGP Flow Specification routes.";
                    }
                    leaf matchPackets {
                      type uint64;
                      config false;
                      description
                        "Number of matched packets.";
                    }
                    leaf matchBytes {
                      type uint64;
                      config false;
                      description
                        "Number of matched bytes.";
                    }
                    leaf matchPacketPer30Sec {
                      type uint64;
                      config false;
                      description
                        "Number of matched packets each 30 seconds.";
                    }
                    leaf matchBytePer30Sec {
                      type uint64;
                      config false;
                      description
                        "Number of matched bytes each 30 seconds.";
                    }
                    leaf trafActFlag {
                      type pub-type:bits8 {
                        ext:masklen 7;
                          ext:bit "route-policy-distribute" {
                            position 1;
                          }
                      }
                      config false;
                      description
                        "Traffic action flag.";
                    }
                    leaf invalidReason {
                      type string {
                        length "0..250";
                      }
                      config false;
                      description
                        "Why a route cannot be delivered to the FIB.";
                    }
                    container wideCommunitys {
                      config false;
                      description
                        "Wide-community information.";
                      list wideCommunity {
                        key "index type flag hopCount";
                        config false;
                        description
                          "Wide-community information.";
                        leaf index {
                          type uint32;
                          config false;
                          description
                            "Index.";
                        }
                        leaf type {
                          type uint32;
                          config false;
                          description
                            "Type.";
                        }
                        leaf flag {
                          type pub-type:hexBinary;
                          config false;
                          description
                            "Flag.";
                        }
                        leaf hopCount {
                          type uint32;
                          config false;
                          description
                            "Hop count.";
                        }
                        leaf communityValue {
                          type pub-type:hexBinary;
                          config false;
                          description
                            "Community value.";
                        }
                        leaf sourceAs {
                          type asNumberValidate;
                          config false;
                          description
                            "Source AS.";
                        }
                        leaf contextAs {
                          type asNumberValidate;
                          config false;
                          description
                            "Context AS.";
                        }
                        leaf param {
                          type string {
                            length "0..2030";
                          }
                          config false;
                          description
                            "Parameter.";
                        }
                      }
                    }
                    container redirectIpRelays {
                      config false;
                      description
                        "Redirection IP information.";
                      list redirectIpRelay {
                        key "redirectIp";
                        config false;
                        description
                          "Redirection IP information.";
                        leaf redirectIp {
                          type inet:ipv4-address-no-zone;
                          config false;
                          description
                            "Redirection IP address.";
                        }
                        leaf redirectOpt {
                          type uint32;
                          config false;
                          description
                            "Operation code.";
                        }
                        leaf redirectResult {
                          type string {
                            length "1..100";
                          }
                          config false;
                          description
                            "Iteration result.";
                        }
                        leaf relayNextHop {
                          type inet:ipv4-address-no-zone;
                          config false;
                          description
                            "IP iteration next hop.";
                        }
                        leaf outIfName {
                          type pub-type:ifName;
                          config false;
                          description
                            "IP iteration outbound interface.";
                        }
                        leaf relayTnlNextHop {
                          type inet:ipv4-address-no-zone;
                          config false;
                          description
                            "Tunnel iteration next hop.";
                        }
                        leaf relayTnlOutIfName {
                          type pub-type:ifName;
                          config false;
                          description
                            "Tunnel iteration outbund interface.";
                        }
                      }
                    }
                    container flowInfGrpStats {
                      config false;
                      description
                        "Statistics of the BGP Flow Specification route with the specified reIndex and flow interface group ID.";
                      list flowInfGrpStat {
                        key "flowIfGrpIndex";
                        config false;
                        description
                          "Statistic of the BGP Flow Specification route with the specified reIndex and flow interface group ID.";
                        leaf flowIfGrpIndex {
                          type uint32 {
                            range "0..16383";
                          }
                          config false;
                          description
                            "Flow interface group ID.";
                        }
                        leaf ruleNumber {
                          type uint64;
                          config false;
                          description
                            "Number of rules for BGP Flow Specification routes.";
                        }
                        leaf matchPackets {
                          type uint64;
                          config false;
                          description
                            "Number of matched packets.";
                        }
                        leaf matchBytes {
                          type uint64;
                          config false;
                          description
                            "Number of matched bytes.";
                        }
                        leaf matchPacketPer30Sec {
                          type uint64;
                          config false;
                          description
                            "Number of matched packets each 30 seconds.";
                        }
                        leaf matchBytePer30Sec {
                          type uint64;
                          config false;
                          description
                            "Number of matched bytes each 30 seconds.";
                        }
                      }
                    }
                  }
                }
                container peerRevRoutingTables {
                  config false;
                  description
                    "List of displayed received route information in an address family.";
                  list peerRevRoutingTable {
                    when "not(../../../../afType!='ipv4uni' and ../../../../afType!='ipv4multi' and ../../../../afType!='ipv4vpn' and ../../../../afType!='ipv6uni' and ../../../../afType!='ipv6vpn')";
                    key "networkPrefix prefixMask routeTypeFlag imTableId rd from pathID";
                    config false;
                    description
                      "Information about received routes.";
                    leaf networkPrefix {
                      type inet:ip-address-no-zone;
                      config false;
                      description
                        "BGP route prefix.";
                    }
                    leaf prefixMask {
                      type uint8;
                      config false;
                      description
                        "Prefix mask.";
                    }
                    leaf routeTypeFlag {
                      type pub-type:bits32 {
                        ext:masklen 32;
                          ext:bit "ibgp" {
                            position 0;
                          }
                          ext:bit "ebgp" {
                            position 1;
                          }
                          ext:bit "network" {
                            position 2;
                          }
                          ext:bit "import" {
                            position 3;
                          }
                          ext:bit "auto-summary" {
                            position 4;
                          }
                          ext:bit "aggregate" {
                            position 5;
                          }
                          ext:bit "cpri" {
                            position 6;
                          }
                          ext:bit "pcri" {
                            position 7;
                          }
                          ext:bit "suppressed" {
                            position 8;
                          }
                          ext:bit "NHP-EMPTY" {
                            position 9;
                          }
                          ext:bit "NO-ADV" {
                            position 10;
                          }
                          ext:bit "local_cross" {
                            position 11;
                          }
                          ext:bit "remote_cross" {
                            position 12;
                          }
                          ext:bit "VD-BGP" {
                            position 13;
                          }
                          ext:bit "PATH_LOCAL" {
                            position 14;
                          }
                          ext:bit "PATH_GATEWAY" {
                            position 15;
                          }
                          ext:bit "policy_nopass" {
                            position 16;
                          }
                          ext:bit "supprenet" {
                            position 17;
                          }
                          ext:bit "dampened" {
                            position 18;
                          }
                          ext:bit "history" {
                            position 19;
                          }
                          ext:bit "select" {
                            position 20;
                          }
                          ext:bit "best" {
                            position 21;
                          }
                          ext:bit "backup" {
                            position 22;
                          }
                          ext:bit "attr_change" {
                            position 23;
                          }
                          ext:bit "NHLFE_CREATED" {
                            position 24;
                          }
                          ext:bit "ILM_CREATED" {
                            position 25;
                          }
                          ext:bit "NEXTHOP_CHANGE" {
                            position 26;
                          }
                          ext:bit "Invaild" {
                            position 27;
                          }
                          ext:bit "SOURCE_CHANGE" {
                            position 28;
                          }
                          ext:bit "IN_SELECTEDQ" {
                            position 29;
                          }
                          ext:bit "EXITIF_ERROR" {
                            position 30;
                          }
                          ext:bit "GROUP_HEAD" {
                            position 31;
                          }
                      }
                      config false;
                      description
                        "Route type.";
                    }
                    leaf imTableId {
                      type uint32 {
                        range "0..4294967295";
                      }
                      config false;
                      description
                        "ID of the routing table to which routes are imported.";
                    }
                    leaf rd {
                      type string {
                        length "1..22";
                      }
                      config false;
                      description
                        "Route distinguisher.";
                    }
                    leaf from {
                      type inet:ip-address-no-zone;
                      config false;
                      description
                        "Source peer that sends a route.";
                    }
                    leaf pathID {
                      type string {
                        length "1..50";
                      }
                      config false;
                      description
                        "Path ID.";
                    }
                    leaf remoteNextHopTunnelAddress {
                      type inet:ip-address-no-zone;
                      config false;
                      description
                        "The remote next hop tunnel address.";
                    }
                    leaf remoteNextHopMacAddress {
                      type pub-type:macAddress;
                      config false;
                      description
                        "The Remote next hop mac.";
                    }
                    leaf nexthop {
                      type inet:ip-address-no-zone;
                      config false;
                      description
                        "Next hop address to which packets are forwarded.";
                    }
                    leaf locPrf {
                      type uint32 {
                        range "0..4294967295";
                      }
                      config false;
                      description
                        "Local priority.The attribute is only fit for the routes from IBGP peer, not suit for which of EBGP peer.";
                    }
                    leaf prefVal {
                      type uint32 {
                        range "0..4294967295";
                      }
                      config false;
                      description
                        "Preferred value of a protocol.";
                    }
                    leaf prefrence {
                      type uint8 {
                        range "0..255";
                      }
                      config false;
                      description
                        "Priority of BGP routes.";
                    }
                    leaf pathAs {
                      type string {
                        length "1..300";
                      }
                      config false;
                      description
                        "List of the AS_Paths that packets pass through.";
                    }
                    leaf origin {
                      type bgpcommOrigin;
                      config false;
                      description
                        "Route origin.";
                    }
                    leaf med {
                      type uint32 {
                        range "0..4294967295";
                      }
                      config false;
                      description
                        "Route MED.The attribute is only fit for the routes from EBGP peer, not suit for which of IBGP peer.";
                    }
                    leaf flagString {
                      type string {
                        length "1..100";
                      }
                      config false;
                      description
                        "Route flag that contains a string of characters.";
                    }
                    leaf rtWorseReason {
                      type string {
                        length "1..50";
                      }
                      config false;
                      description
                        "Reason why a route is not selected.";
                    }
                    leaf peerString {
                      type string {
                        length "1..300";
                      }
                      config false;
                      description
                        "List of route sending peers.";
                    }
                    leaf time {
                      type uint32 {
                        range "0..4294967295";
                      }
                      config false;
                      description
                        "Time stamp of a route.";
                    }
                    leaf community {
                      type string {
                        length "1..120";
                      }
                      config false;
                      description
                        "Community attribute.";
                    }
                    leaf extCommunity {
                      type string {
                        length "1..300";
                      }
                      config false;
                      description
                        "Extended community attribute.";
                    }
                    leaf ifName {
                      type leafref {
                        path "/ifm:ifm/ifm:interfaces/ifm:interface/ifm:ifName";
                      }
                      config false;
                      description
                        "Name of the outbound interface of a route.";
                    }
                    leaf originator {
                      type inet:ip-address-no-zone;
                      config false;
                      description
                        "Router ID of the route initiator.";
                    }
                    leaf clusterList {
                      type string {
                        length "1..300";
                      }
                      config false;
                      description
                        "List of cluster IDs.";
                    }
                    leaf remoteRouteId {
                      type inet:ipv4-address-no-zone;
                      config false;
                      description
                        "Router ID of a peer.";
                    }
                    leaf relayNexthop {
                      type inet:ip-address-no-zone;
                      config false;
                      description
                        "Next hop to which a route is iterated.";
                    }
                    leaf relaytnlName {
                      type string {
                        length "1..64";
                      }
                      config false;
                      description
                        "Name of a tunnel to which a route is iterated.";
                    }
                    leaf isAtomicAggre {
                      type boolean;
                      default "false";
                      config false;
                      description
                        "Route carrying the atomic-aggregate attribute.";
                    }
                    leaf aggregatorAs {
                      type string {
                        length "1..11";
                      }
                      config false;
                      description
                        "AS number of the route summarizer.";
                    }
                    leaf aggregatorId {
                      type inet:ip-address-no-zone;
                      config false;
                      description
                        "ID of the route summarizer.";
                    }
                    leaf inLabel {
                      type uint32 {
                        range "0..4294967295";
                      }
                      config false;
                      description
                        "In-label.";
                    }
                    leaf outLabel {
                      type uint32 {
                        range "0..4294967295";
                      }
                      config false;
                      description
                        "Out-label.";
                    }
                    leaf disAttrString {
                      type string {
                        length "1..300";
                      }
                      config false;
                      description
                        "Discard the route attribute list.";
                    }
                    leaf vrfName {
                      type string {
                        length "1..31";
                      }
                      config false;
                      description
                        "Iterated Vrf .";
                    }
                    leaf remoteNextHopVni {
                      type uint32 {
                        range "0..4294967295";
                      }
                      config false;
                      description
                        "The remote next hop vni.";
                    }
                    leaf advNextHop {
                      type inet:ip-address-no-zone;
                      config false;
                      description
                        "Advertised Nexthop.";
                    }
                    leaf prefixSid {
                      type string {
                        length "1..60";
                      }
                      config false;
                      description
                        "PrefixSid attribute information of Route.";
                    }
                    leaf aigp {
                      type uint64;
                      config false;
                      description
                        "AIGP attribute information of Route.";
                    }
                    leaf attrSetString {
                      type string {
                        length "1..300";
                      }
                      config false;
                      description
                        "The attribute set information of Route.";
                    }
                  }
                }
                container peerAdvRoutingTables {
                  config false;
                  description
                    "List of displayed advertised route information in an address family.";
                  list peerAdvRoutingTable {
                    when "not(../../../../afType!='ipv4uni' and ../../../../afType!='ipv4multi' and ../../../../afType!='ipv4vpn' and ../../../../afType!='ipv6uni' and ../../../../afType!='ipv6vpn')";
                    key "networkPrefix prefixMask routeTypeFlag imTableId rd from pathID";
                    config false;
                    description
                      "Information about advertised routes.";
                    leaf networkPrefix {
                      type inet:ip-address-no-zone;
                      config false;
                      description
                        "BGP route prefix.";
                    }
                    leaf prefixMask {
                      type uint8;
                      config false;
                      description
                        "Prefix mask.";
                    }
                    leaf routeTypeFlag {
                      type pub-type:bits32 {
                        ext:masklen 32;
                          ext:bit "ibgp" {
                            position 0;
                          }
                          ext:bit "ebgp" {
                            position 1;
                          }
                          ext:bit "network" {
                            position 2;
                          }
                          ext:bit "import" {
                            position 3;
                          }
                          ext:bit "auto-summary" {
                            position 4;
                          }
                          ext:bit "aggregate" {
                            position 5;
                          }
                          ext:bit "cpri" {
                            position 6;
                          }
                          ext:bit "pcri" {
                            position 7;
                          }
                          ext:bit "suppressed" {
                            position 8;
                          }
                          ext:bit "NHP-EMPTY" {
                            position 9;
                          }
                          ext:bit "NO-ADV" {
                            position 10;
                          }
                          ext:bit "local_cross" {
                            position 11;
                          }
                          ext:bit "remote_cross" {
                            position 12;
                          }
                          ext:bit "VD-BGP" {
                            position 13;
                          }
                          ext:bit "PATH_LOCAL" {
                            position 14;
                          }
                          ext:bit "PATH_GATEWAY" {
                            position 15;
                          }
                          ext:bit "policy_nopass" {
                            position 16;
                          }
                          ext:bit "supprenet" {
                            position 17;
                          }
                          ext:bit "dampened" {
                            position 18;
                          }
                          ext:bit "history" {
                            position 19;
                          }
                          ext:bit "select" {
                            position 20;
                          }
                          ext:bit "best" {
                            position 21;
                          }
                          ext:bit "backup" {
                            position 22;
                          }
                          ext:bit "attr_change" {
                            position 23;
                          }
                          ext:bit "NHLFE_CREATED" {
                            position 24;
                          }
                          ext:bit "ILM_CREATED" {
                            position 25;
                          }
                          ext:bit "NEXTHOP_CHANGE" {
                            position 26;
                          }
                          ext:bit "Invaild" {
                            position 27;
                          }
                          ext:bit "SOURCE_CHANGE" {
                            position 28;
                          }
                          ext:bit "IN_SELECTEDQ" {
                            position 29;
                          }
                          ext:bit "EXITIF_ERROR" {
                            position 30;
                          }
                          ext:bit "GROUP_HEAD" {
                            position 31;
                          }
                      }
                      config false;
                      description
                        "Route type.";
                    }
                    leaf imTableId {
                      type uint32 {
                        range "0..4294967295";
                      }
                      config false;
                      description
                        "ID of the routing table to which routes are imported.";
                    }
                    leaf rd {
                      type string {
                        length "1..22";
                      }
                      config false;
                      description
                        "Route distinguisher.";
                    }
                    leaf from {
                      type inet:ip-address-no-zone;
                      config false;
                      description
                        "Source peer that sends a route.";
                    }
                    leaf pathID {
                      type string {
                        length "1..50";
                      }
                      config false;
                      description
                        "Path ID.";
                    }
                    leaf remoteNextHopTunnelAddress {
                      type inet:ip-address-no-zone;
                      config false;
                      description
                        "The remote next hop tunnel address.";
                    }
                    leaf remoteNextHopMacAddress {
                      type pub-type:macAddress;
                      config false;
                      description
                        "The Remote next hop mac.";
                    }
                    leaf nexthop {
                      type inet:ip-address-no-zone;
                      config false;
                      description
                        "Next hop address to which packets are forwarded.";
                    }
                    leaf locPrf {
                      type uint32 {
                        range "0..4294967295";
                      }
                      config false;
                      description
                        "Local priority.The attribute is only fit for the routes from IBGP peer, not suit for which of EBGP peer.";
                    }
                    leaf prefVal {
                      type uint32 {
                        range "0..4294967295";
                      }
                      config false;
                      description
                        "Preferred value of a protocol.";
                    }
                    leaf prefrence {
                      type uint8 {
                        range "0..255";
                      }
                      config false;
                      description
                        "Priority of BGP routes.";
                    }
                    leaf pathAs {
                      type string {
                        length "1..300";
                      }
                      config false;
                      description
                        "List of the AS_Paths that packets pass through.";
                    }
                    leaf origin {
                      type bgpcommOrigin;
                      config false;
                      description
                        "Route origin.";
                    }
                    leaf med {
                      type uint32 {
                        range "0..4294967295";
                      }
                      config false;
                      description
                        "Route MED.The attribute is only fit for the routes from EBGP peer, not suit for which of IBGP peer.";
                    }
                    leaf flagString {
                      type string {
                        length "1..100";
                      }
                      config false;
                      description
                        "Route flag that contains a string of characters.";
                    }
                    leaf rtWorseReason {
                      type string {
                        length "1..50";
                      }
                      config false;
                      description
                        "Reason why a route is not selected.";
                    }
                    leaf peerString {
                      type string {
                        length "1..300";
                      }
                      config false;
                      description
                        "List of route sending peers.";
                    }
                    leaf time {
                      type uint32 {
                        range "0..4294967295";
                      }
                      config false;
                      description
                        "Time stamp of a route.";
                    }
                    leaf community {
                      type string {
                        length "1..120";
                      }
                      config false;
                      description
                        "Community attribute.";
                    }
                    leaf extCommunity {
                      type string {
                        length "1..300";
                      }
                      config false;
                      description
                        "Extended community attribute.";
                    }
                    leaf ifName {
                      type leafref {
                        path "/ifm:ifm/ifm:interfaces/ifm:interface/ifm:ifName";
                      }
                      config false;
                      description
                        "Name of the outbound interface of a route.";
                    }
                    leaf originator {
                      type inet:ip-address-no-zone;
                      config false;
                      description
                        "Router ID of the route initiator.";
                    }
                    leaf clusterList {
                      type string {
                        length "1..300";
                      }
                      config false;
                      description
                        "List of cluster IDs.";
                    }
                    leaf remoteRouteId {
                      type inet:ipv4-address-no-zone;
                      config false;
                      description
                        "Router ID of a peer.";
                    }
                    leaf relayNexthop {
                      type inet:ip-address-no-zone;
                      config false;
                      description
                        "Next hop to which a route is iterated.";
                    }
                    leaf relaytnlName {
                      type string {
                        length "1..64";
                      }
                      config false;
                      description
                        "Name of a tunnel to which a route is iterated.";
                    }
                    leaf isAtomicAggre {
                      type boolean;
                      default "false";
                      config false;
                      description
                        "Route carrying the atomic-aggregate attribute.";
                    }
                    leaf aggregatorAs {
                      type string {
                        length "1..11";
                      }
                      config false;
                      description
                        "AS number of the route summarizer.";
                    }
                    leaf aggregatorId {
                      type inet:ip-address-no-zone;
                      config false;
                      description
                        "ID of the route summarizer.";
                    }
                    leaf inLabel {
                      type uint32 {
                        range "0..4294967295";
                      }
                      config false;
                      description
                        "In-label.";
                    }
                    leaf outLabel {
                      type uint32 {
                        range "0..4294967295";
                      }
                      config false;
                      description
                        "Out-label.";
                    }
                    leaf disAttrString {
                      type string {
                        length "1..300";
                      }
                      config false;
                      description
                        "Discard the route attribute list.";
                    }
                    leaf vrfName {
                      type string {
                        length "1..31";
                      }
                      config false;
                      description
                        "Iterated Vrf .";
                    }
                    leaf remoteNextHopVni {
                      type uint32 {
                        range "0..4294967295";
                      }
                      config false;
                      description
                        "The remote next hop vni.";
                    }
                    leaf advNextHop {
                      type inet:ip-address-no-zone;
                      config false;
                      description
                        "Advertised Nexthop.";
                    }
                    leaf prefixSid {
                      type string {
                        length "1..60";
                      }
                      config false;
                      description
                        "PrefixSid attribute information of Route.";
                    }
                    leaf aigp {
                      type uint64;
                      config false;
                      description
                        "AIGP attribute information of Route.";
                    }
                    leaf attrSetString {
                      type string {
                        length "1..300";
                      }
                      config false;
                      description
                        "The attribute set information of Route.";
                    }
                  }
                }
                container peerlsNodeRevRtTables {
                  config false;
                  description
                    "LS node route list.";
                  list peerlsNodeRevRtTable {
                    when "../../../../afType='ls'";
                    key "routeType protocolType identifier lsNetwork nexthop from peerRID";
                    config false;
                    description
                      "LS node route.";
                    leaf routeType {
                      type bgpcommLsRouteType;
                      config false;
                      description
                        "BGP-LS Route Type.";
                    }
                    leaf protocolType {
                      type bgpcommLsProtocolType;
                      config false;
                      description
                        "IGP Protocol type.";
                    }
                    leaf identifier {
                      type uint64 {
                        range "2..65535";
                      }
                      config false;
                      description
                        "Identifier of IGP protocol.";
                    }
                    leaf lsNetwork {
                      type string {
                        length "1..600";
                      }
                      config false;
                      description
                        "Prefix of BGP-LS route.";
                    }
                    leaf routeTypeFlag {
                      type pub-type:bits32 {
                        ext:masklen 32;
                          ext:bit "ibgp" {
                            position 0;
                          }
                          ext:bit "ebgp" {
                            position 1;
                          }
                          ext:bit "network" {
                            position 2;
                          }
                          ext:bit "import" {
                            position 3;
                          }
                          ext:bit "auto-summary" {
                            position 4;
                          }
                          ext:bit "aggregate" {
                            position 5;
                          }
                          ext:bit "cpri" {
                            position 6;
                          }
                          ext:bit "pcri" {
                            position 7;
                          }
                          ext:bit "suppressed" {
                            position 8;
                          }
                          ext:bit "NHP-EMPTY" {
                            position 9;
                          }
                          ext:bit "NO-ADV" {
                            position 10;
                          }
                          ext:bit "local_cross" {
                            position 11;
                          }
                          ext:bit "remote_cross" {
                            position 12;
                          }
                          ext:bit "VD-BGP" {
                            position 13;
                          }
                          ext:bit "PATH_LOCAL" {
                            position 14;
                          }
                          ext:bit "PATH_GATEWAY" {
                            position 15;
                          }
                          ext:bit "policy_nopass" {
                            position 16;
                          }
                          ext:bit "supprenet" {
                            position 17;
                          }
                          ext:bit "dampened" {
                            position 18;
                          }
                          ext:bit "history" {
                            position 19;
                          }
                          ext:bit "select" {
                            position 20;
                          }
                          ext:bit "best" {
                            position 21;
                          }
                          ext:bit "backup" {
                            position 22;
                          }
                          ext:bit "attr_change" {
                            position 23;
                          }
                          ext:bit "NHLFE_CREATED" {
                            position 24;
                          }
                          ext:bit "ILM_CREATED" {
                            position 25;
                          }
                          ext:bit "NEXTHOP_CHANGE" {
                            position 26;
                          }
                          ext:bit "Invaild" {
                            position 27;
                          }
                          ext:bit "SOURCE_CHANGE" {
                            position 28;
                          }
                          ext:bit "IN_SELECTEDQ" {
                            position 29;
                          }
                          ext:bit "EXITIF_ERROR" {
                            position 30;
                          }
                          ext:bit "GROUP_HEAD" {
                            position 31;
                          }
                      }
                      config false;
                      description
                        "Route type.";
                    }
                    leaf nexthop {
                      type inet:ip-address-no-zone;
                      config false;
                      description
                        "Next hop address to which packets are forwarded.";
                    }
                    leaf flagString {
                      type string {
                        length "1..100";
                      }
                      config false;
                      description
                        "Route flag that contains a string of characters.";
                    }
                    leaf locPrf {
                      type uint32 {
                        range "0..4294967295";
                      }
                      config false;
                      description
                        "Local priority.The attribute is only fit for the routes from IBGP peer, not suit for which of EBGP peer.";
                    }
                    leaf prefVal {
                      type uint32 {
                        range "0..4294967295";
                      }
                      config false;
                      description
                        "Preferred value of a protocol.";
                    }
                    leaf prefrence {
                      type uint8 {
                        range "0..255";
                      }
                      config false;
                      description
                        "Preference of a route.";
                    }
                    leaf pathAs {
                      type string {
                        length "1..300";
                      }
                      config false;
                      description
                        "List of the ASs that packets pass through.";
                    }
                    leaf med {
                      type uint32 {
                        range "0..4294967295";
                      }
                      config false;
                      description
                        "Route MED in the attribute node.The attribute is only fit for the routes from EBGP peer, not suit for which of IBGP peer.";
                    }
                    leaf rtWorseReason {
                      type string {
                        length "1..50";
                      }
                      config false;
                      description
                        "Reason why a route is not selected.";
                    }
                    leaf time {
                      type uint32 {
                        range "0..4294967295";
                      }
                      config false;
                      description
                        "Time stamp of a route.";
                    }
                    leaf from {
                      type inet:ip-address-no-zone;
                      config false;
                      description
                        "Source peer that sends a route.";
                    }
                    leaf peerRID {
                      type inet:ip-address-no-zone;
                      config false;
                      description
                        "Router ID of source peer that sends a route.";
                    }
                    leaf ifName {
                      type pub-type:ifName;
                      config false;
                      description
                        "Name of the outbound interface of a route.";
                    }
                    leaf originator {
                      type inet:ip-address-no-zone;
                      config false;
                      description
                        "Router ID of the route initiator.";
                    }
                    leaf relayNexthop {
                      type inet:ip-address-no-zone;
                      config false;
                      description
                        "Next hop to which a route is iterated.";
                    }
                    leaf disAttrString {
                      type string {
                        length "1..300";
                      }
                      config false;
                      description
                        "Discard the route attribute list.";
                    }
                    leaf inLabel {
                      type uint32;
                      config false;
                      description
                        "In-label.";
                    }
                    leaf outLabel {
                      type uint32;
                      config false;
                      description
                        "Out-label.";
                    }
                    leaf mtIdVarAttrStr {
                      type string {
                        length "1..300";
                      }
                      config false;
                      description
                        "MT ID.";
                    }
                    leaf nodeName {
                      type string {
                        length "1..300";
                      }
                      config false;
                      description
                        "Name of IGP topology node.";
                    }
                    leaf isisAreaIdStr {
                      type string {
                        length "1..300";
                      }
                      config false;
                      description
                        "ISIS area ID.";
                    }
                    leaf sidLabelBinding {
                      type string {
                        length "1..300";
                      }
                      config false;
                      description
                        "SID/Label Binding.";
                    }
                    leaf srCapabilities {
                      type string {
                        length "1..300";
                      }
                      config false;
                      description
                        "Segment routing capabilities.";
                    }
                    leaf srAlgorithmStr {
                      type string {
                        length "1..300";
                      }
                      config false;
                      description
                        "Segment routing algorithm.";
                    }
                    leaf nodeFlagBits {
                      type pub-type:hexBinary;
                      config false;
                      description
                        "Node flags.";
                    }
                    leaf ipv4RouterIdOfLocalNode {
                      type string {
                        length "1..300";
                      }
                      config false;
                      description
                        "Ipv4 router id of local node.";
                    }
                    leaf ipv6RouterIdOfLocalNode {
                      type string {
                        length "1..300";
                      }
                      config false;
                      description
                        "Ipv6 router id of local node.";
                    }
                    leaf opaqueNodeProp {
                      type string {
                        length "1..300";
                      }
                      config false;
                      description
                        "Opaque node properties.";
                    }
                    leaf peerCount {
                      type uint32;
                      config false;
                      description
                        "Count of route sending peers.";
                    }
                    leaf advPeerListStr {
                      type string {
                        length "1..300";
                      }
                      config false;
                      description
                        "List of route sending peers.";
                    }
                  }
                }
                container peerlsLinkRevRtTables {
                  config false;
                  description
                    "List of link routes.";
                  list peerlsLinkRevRtTable {
                    when "../../../../afType='ls'";
                    key "routeType protocolType identifier lsNetwork nexthop from peerRID";
                    config false;
                    description
                      "Link route.";
                    leaf routeType {
                      type bgpcommLsRouteType;
                      config false;
                      description
                        "BGP-LS Route Type.";
                    }
                    leaf protocolType {
                      type bgpcommLsProtocolType;
                      config false;
                      description
                        "IGP Protocol type.";
                    }
                    leaf identifier {
                      type uint64 {
                        range "2..65535";
                      }
                      config false;
                      description
                        "Identifier of IGP protocol.";
                    }
                    leaf lsNetwork {
                      type string {
                        length "1..600";
                      }
                      config false;
                      description
                        "Prefix of BGP-LS route.";
                    }
                    leaf routeTypeFlag {
                      type pub-type:bits32 {
                        ext:masklen 32;
                          ext:bit "ibgp" {
                            position 0;
                          }
                          ext:bit "ebgp" {
                            position 1;
                          }
                          ext:bit "network" {
                            position 2;
                          }
                          ext:bit "import" {
                            position 3;
                          }
                          ext:bit "auto-summary" {
                            position 4;
                          }
                          ext:bit "aggregate" {
                            position 5;
                          }
                          ext:bit "cpri" {
                            position 6;
                          }
                          ext:bit "pcri" {
                            position 7;
                          }
                          ext:bit "suppressed" {
                            position 8;
                          }
                          ext:bit "NHP-EMPTY" {
                            position 9;
                          }
                          ext:bit "NO-ADV" {
                            position 10;
                          }
                          ext:bit "local_cross" {
                            position 11;
                          }
                          ext:bit "remote_cross" {
                            position 12;
                          }
                          ext:bit "VD-BGP" {
                            position 13;
                          }
                          ext:bit "PATH_LOCAL" {
                            position 14;
                          }
                          ext:bit "PATH_GATEWAY" {
                            position 15;
                          }
                          ext:bit "policy_nopass" {
                            position 16;
                          }
                          ext:bit "supprenet" {
                            position 17;
                          }
                          ext:bit "dampened" {
                            position 18;
                          }
                          ext:bit "history" {
                            position 19;
                          }
                          ext:bit "select" {
                            position 20;
                          }
                          ext:bit "best" {
                            position 21;
                          }
                          ext:bit "backup" {
                            position 22;
                          }
                          ext:bit "attr_change" {
                            position 23;
                          }
                          ext:bit "NHLFE_CREATED" {
                            position 24;
                          }
                          ext:bit "ILM_CREATED" {
                            position 25;
                          }
                          ext:bit "NEXTHOP_CHANGE" {
                            position 26;
                          }
                          ext:bit "Invaild" {
                            position 27;
                          }
                          ext:bit "SOURCE_CHANGE" {
                            position 28;
                          }
                          ext:bit "IN_SELECTEDQ" {
                            position 29;
                          }
                          ext:bit "EXITIF_ERROR" {
                            position 30;
                          }
                          ext:bit "GROUP_HEAD" {
                            position 31;
                          }
                      }
                      config false;
                      description
                        "Route type.";
                    }
                    leaf nexthop {
                      type inet:ip-address-no-zone;
                      config false;
                      description
                        "Next hop address to which packets are forwarded.";
                    }
                    leaf flagString {
                      type string {
                        length "1..100";
                      }
                      config false;
                      description
                        "Route flag that contains a string of characters.";
                    }
                    leaf locPrf {
                      type uint32 {
                        range "0..4294967295";
                      }
                      config false;
                      description
                        "Local priority.The attribute is only fit for the routes from IBGP peer, not suit for which of EBGP peer.";
                    }
                    leaf prefVal {
                      type uint32 {
                        range "0..4294967295";
                      }
                      config false;
                      description
                        "Preferred value of a protocol.";
                    }
                    leaf prefrence {
                      type uint8 {
                        range "0..255";
                      }
                      config false;
                      description
                        "Preference of a route.";
                    }
                    leaf pathAs {
                      type string {
                        length "1..300";
                      }
                      config false;
                      description
                        "List of the ASs that packets pass through.";
                    }
                    leaf med {
                      type uint32 {
                        range "0..4294967295";
                      }
                      config false;
                      description
                        "Route MED in the attribute node.The attribute is only fit for the routes from EBGP peer, not suit for which of IBGP peer.";
                    }
                    leaf rtWorseReason {
                      type string {
                        length "1..50";
                      }
                      config false;
                      description
                        "Reason why a route is not selected.";
                    }
                    leaf time {
                      type uint32 {
                        range "0..4294967295";
                      }
                      config false;
                      description
                        "Time stamp of a route.";
                    }
                    leaf from {
                      type inet:ip-address-no-zone;
                      config false;
                      description
                        "Source peer that sends a route.";
                    }
                    leaf peerRID {
                      type inet:ip-address-no-zone;
                      config false;
                      description
                        "Router ID of source peer that sends a route.";
                    }
                    leaf ifName {
                      type pub-type:ifName;
                      config false;
                      description
                        "Name of the outbound interface of a route.";
                    }
                    leaf originator {
                      type inet:ip-address-no-zone;
                      config false;
                      description
                        "Router ID of the route initiator.";
                    }
                    leaf relayNexthop {
                      type inet:ip-address-no-zone;
                      config false;
                      description
                        "Next hop to which a route is iterated.";
                    }
                    leaf disAttrString {
                      type string {
                        length "1..300";
                      }
                      config false;
                      description
                        "Discard the route attribute list.";
                    }
                    leaf inLabel {
                      type uint32;
                      config false;
                      description
                        "In-label.";
                    }
                    leaf outLabel {
                      type uint32;
                      config false;
                      description
                        "Out-label.";
                    }
                    leaf ipv4RouterIdOfLocalNode {
                      type string {
                        length "1..300";
                      }
                      config false;
                      description
                        "Ipv4 router id of local node.";
                    }
                    leaf ipv6RouterIdOfLocalNode {
                      type string {
                        length "1..300";
                      }
                      config false;
                      description
                        "Ipv6 router id of local node.";
                    }
                    leaf ipv4RouterIdOfRemoteNode {
                      type string {
                        length "1..300";
                      }
                      config false;
                      description
                        "Ipv4 router id of remote node.";
                    }
                    leaf ipv6RouterIdOfRemoteNode {
                      type string {
                        length "1..300";
                      }
                      config false;
                      description
                        "Ipv6 router id of remote node.";
                    }
                    leaf adminGroupColor {
                      type pub-type:hexBinary;
                      config false;
                      description
                        "adminGroupColor.";
                    }
                    leaf maxLinkBandWidth {
                      type uint32;
                      config false;
                      description
                        "Maximum Link Bandwidth(kbits/sec).";
                    }
                    leaf maxResvLinkBandWidth {
                      type uint32;
                      config false;
                      description
                        "Maximum Reservable Bandwidth(kbits/sec).";
                    }
                    leaf unResvBandWidth {
                      type string {
                        length "1..300";
                      }
                      config false;
                      description
                        "Maximum Unreserved Bandwidth(kbits/sec).";
                    }
                    leaf teDefaultMetric {
                      type uint32;
                      config false;
                      description
                        "teDefaultMetric.";
                    }
                    leaf linkProtectType {
                      type pub-type:bits16 {
                        ext:masklen 16;
                          ext:bit "null" {
                            position 0;
                          }
                          ext:bit "Extra Traffic" {
                            position 1;
                          }
                          ext:bit "Unprotected" {
                            position 2;
                          }
                          ext:bit "Shared" {
                            position 3;
                          }
                          ext:bit "Dedicated 1:1" {
                            position 4;
                          }
                          ext:bit "Dedicated 1+1" {
                            position 5;
                          }
                          ext:bit "Enhanced" {
                            position 6;
                          }
                          ext:bit "null7" {
                            position 7;
                          }
                          ext:bit "null8" {
                            position 8;
                          }
                          ext:bit "null9" {
                            position 9;
                          }
                          ext:bit "null10" {
                            position 10;
                          }
                          ext:bit "null11" {
                            position 11;
                          }
                          ext:bit "null12" {
                            position 12;
                          }
                          ext:bit "null13" {
                            position 13;
                          }
                          ext:bit "null14" {
                            position 14;
                          }
                          ext:bit "null15" {
                            position 15;
                          }
                      }
                      config false;
                      description
                        "Link Protect Type.";
                    }
                    leaf mplsProtocolMask {
                      type pub-type:hexBinary;
                      config false;
                      description
                        "mplsProtocolMask.";
                    }
                    leaf igpMetric {
                      type uint32;
                      config false;
                      description
                        "igpMetric.";
                    }
                    leaf shareRiskLGStr {
                      type string {
                        length "1..300";
                      }
                      config false;
                      description
                        "shareRiskLGStr.";
                    }
                    leaf opaqueLinkProp {
                      type string {
                        length "1..300";
                      }
                      config false;
                      description
                        "Opaque link properties.";
                    }
                    leaf linkName {
                      type string {
                        length "1..300";
                      }
                      config false;
                      description
                        "Link name.";
                    }
                    leaf adjSegmentId {
                      type string {
                        length "1..300";
                      }
                      config false;
                      description
                        "adjSegmentId.";
                    }
                    leaf lanAdjSegmentId {
                      type string {
                        length "1..300";
                      }
                      config false;
                      description
                        "lanAdjSegmentId.";
                    }
                    leaf unresrvBwBc0 {
                      type string {
                        length "1..20";
                      }
                      config false;
                      description
                        "Unreserved Bandwidth.";
                    }
                    leaf bwConstraintModel {
                      type string {
                        length "1..20";
                      }
                      config false;
                      description
                        "Bandwidth Constraint Model.";
                    }
                    leaf bwConstraintBc0 {
                      type string {
                        length "1..20";
                      }
                      config false;
                      description
                        "Bandwidth Constraint.";
                    }
                    leaf loMultiBc0 {
                      type string {
                        length "1..10";
                      }
                      config false;
                      description
                        "Local Overbooking Multiplier.";
                    }
                    leaf bwConstModelStd {
                      type string {
                        length "1..20";
                      }
                      config false;
                      description
                        "Bandwidth Constraint Model(Standard).";
                    }
                    leaf bwConstBc0Std {
                      type string {
                        length "1..20";
                      }
                      config false;
                      description
                        "Bandwidth Constraint(Standard).";
                    }
                    leaf peerCount {
                      type uint32;
                      config false;
                      description
                        "Count of route sending peers.";
                    }
                    leaf advPeerListStr {
                      type string {
                        length "1..300";
                      }
                      config false;
                      description
                        "List of route sending peers.";
                    }
                  }
                }
                container peerlsPrefixRevRtTables {
                  config false;
                  description
                    "List of prefix routes.";
                  list peerlsPrefixRevRtTable {
                    when "../../../../afType='ls'";
                    key "routeType protocolType identifier lsNetwork nexthop from peerRID";
                    config false;
                    description
                      "Prefix route.";
                    leaf routeType {
                      type bgpcommLsRouteType;
                      config false;
                      description
                        "BGP-LS Route Type.";
                    }
                    leaf protocolType {
                      type bgpcommLsProtocolType;
                      config false;
                      description
                        "IGP Protocol type.";
                    }
                    leaf identifier {
                      type uint64 {
                        range "2..65535";
                      }
                      config false;
                      description
                        "Identifier of IGP protocol.";
                    }
                    leaf lsNetwork {
                      type string {
                        length "1..600";
                      }
                      config false;
                      description
                        "Prefix of BGP-LS route.";
                    }
                    leaf routeTypeFlag {
                      type pub-type:bits32 {
                        ext:masklen 32;
                          ext:bit "ibgp" {
                            position 0;
                          }
                          ext:bit "ebgp" {
                            position 1;
                          }
                          ext:bit "network" {
                            position 2;
                          }
                          ext:bit "import" {
                            position 3;
                          }
                          ext:bit "auto-summary" {
                            position 4;
                          }
                          ext:bit "aggregate" {
                            position 5;
                          }
                          ext:bit "cpri" {
                            position 6;
                          }
                          ext:bit "pcri" {
                            position 7;
                          }
                          ext:bit "suppressed" {
                            position 8;
                          }
                          ext:bit "NHP-EMPTY" {
                            position 9;
                          }
                          ext:bit "NO-ADV" {
                            position 10;
                          }
                          ext:bit "local_cross" {
                            position 11;
                          }
                          ext:bit "remote_cross" {
                            position 12;
                          }
                          ext:bit "VD-BGP" {
                            position 13;
                          }
                          ext:bit "PATH_LOCAL" {
                            position 14;
                          }
                          ext:bit "PATH_GATEWAY" {
                            position 15;
                          }
                          ext:bit "policy_nopass" {
                            position 16;
                          }
                          ext:bit "supprenet" {
                            position 17;
                          }
                          ext:bit "dampened" {
                            position 18;
                          }
                          ext:bit "history" {
                            position 19;
                          }
                          ext:bit "select" {
                            position 20;
                          }
                          ext:bit "best" {
                            position 21;
                          }
                          ext:bit "backup" {
                            position 22;
                          }
                          ext:bit "attr_change" {
                            position 23;
                          }
                          ext:bit "NHLFE_CREATED" {
                            position 24;
                          }
                          ext:bit "ILM_CREATED" {
                            position 25;
                          }
                          ext:bit "NEXTHOP_CHANGE" {
                            position 26;
                          }
                          ext:bit "Invaild" {
                            position 27;
                          }
                          ext:bit "SOURCE_CHANGE" {
                            position 28;
                          }
                          ext:bit "IN_SELECTEDQ" {
                            position 29;
                          }
                          ext:bit "EXITIF_ERROR" {
                            position 30;
                          }
                          ext:bit "GROUP_HEAD" {
                            position 31;
                          }
                      }
                      config false;
                      description
                        "Route type.";
                    }
                    leaf nexthop {
                      type inet:ip-address-no-zone;
                      config false;
                      description
                        "Next hop address to which packets are forwarded.";
                    }
                    leaf flagString {
                      type string {
                        length "1..100";
                      }
                      config false;
                      description
                        "Route flag that contains a string of characters.";
                    }
                    leaf locPrf {
                      type uint32 {
                        range "0..4294967295";
                      }
                      config false;
                      description
                        "Local priority.The attribute is only fit for the routes from IBGP peer, not suit for which of EBGP peer.";
                    }
                    leaf prefVal {
                      type uint32 {
                        range "0..4294967295";
                      }
                      config false;
                      description
                        "Preferred value of a protocol.";
                    }
                    leaf prefrence {
                      type uint8 {
                        range "0..255";
                      }
                      config false;
                      description
                        "Preference of a route.";
                    }
                    leaf pathAs {
                      type string {
                        length "1..300";
                      }
                      config false;
                      description
                        "List of the ASs that packets pass through.";
                    }
                    leaf med {
                      type uint32 {
                        range "0..4294967295";
                      }
                      config false;
                      description
                        "Route MED in the attribute node.The attribute is only fit for the routes from EBGP peer, not suit for which of IBGP peer.";
                    }
                    leaf rtWorseReason {
                      type string {
                        length "1..50";
                      }
                      config false;
                      description
                        "Reason why a route is not selected.";
                    }
                    leaf time {
                      type uint32 {
                        range "0..4294967295";
                      }
                      config false;
                      description
                        "Time stamp of a route.";
                    }
                    leaf from {
                      type inet:ip-address-no-zone;
                      config false;
                      description
                        "Source peer that sends a route.";
                    }
                    leaf peerRID {
                      type inet:ip-address-no-zone;
                      config false;
                      description
                        "Router ID of source peer that sends a route.";
                    }
                    leaf ifName {
                      type pub-type:ifName;
                      config false;
                      description
                        "Name of the outbound interface of a route.";
                    }
                    leaf originator {
                      type inet:ip-address-no-zone;
                      config false;
                      description
                        "Router ID of the route initiator.";
                    }
                    leaf relayNexthop {
                      type inet:ip-address-no-zone;
                      config false;
                      description
                        "Next hop to which a route is iterated.";
                    }
                    leaf disAttrString {
                      type string {
                        length "1..300";
                      }
                      config false;
                      description
                        "Discard the route attribute list.";
                    }
                    leaf inLabel {
                      type uint32;
                      config false;
                      description
                        "In-label.";
                    }
                    leaf outLabel {
                      type uint32;
                      config false;
                      description
                        "Out-label.";
                    }
                    leaf igpFlags {
                      type pub-type:hexBinary;
                      config false;
                      description
                        "IGP flags.";
                    }
                    leaf routeTags {
                      type string {
                        length "1..300";
                      }
                      config false;
                      description
                        "Route tag.";
                    }
                    leaf extRouteTag {
                      type string {
                        length "1..300";
                      }
                      config false;
                      description
                        "Extended route tag.";
                    }
                    leaf prefixMetric {
                      type uint32;
                      config false;
                      description
                        "prefixMetric.";
                    }
                    leaf ospfForwAddr {
                      type inet:ip-address-no-zone;
                      config false;
                      description
                        "ospfForwAddr.";
                    }
                    leaf opaquePrefixAtt {
                      type inet:ip-address-no-zone;
                      config false;
                      description
                        "Opaque prefix attribute.";
                    }
                    leaf prefixSID {
                      type string {
                        length "1..300";
                      }
                      config false;
                      description
                        "prefixSID.";
                    }
                    leaf peerCount {
                      type uint32;
                      config false;
                      description
                        "Count of route sending peers.";
                    }
                    leaf advPeerListStr {
                      type string {
                        length "1..300";
                      }
                      config false;
                      description
                        "List of route sending peers.";
                    }
                  }
                }
                container peerAcceptRtTables {
                  config false;
                  description
                    "List of displayed route information in an address family.";
                  list peerAcceptRtTable {
                    when "not(../../../../afType!='ipv4uni' and ../../../../afType!='ipv4multi' and ../../../../afType!='ipv4vpn' and ../../../../afType!='ipv6uni' and ../../../../afType!='ipv6vpn')";
                    key "networkPrefix prefixMask routeTypeFlag imTableId rd from pathID";
                    config false;
                    description
                      "Information about routes.";
                    leaf networkPrefix {
                      type inet:ip-address-no-zone;
                      config false;
                      description
                        "BGP route prefix.";
                    }
                    leaf prefixMask {
                      type uint8;
                      config false;
                      description
                        "Prefix mask.";
                    }
                    leaf routeTypeFlag {
                      type pub-type:bits32 {
                        ext:masklen 32;
                          ext:bit "ibgp" {
                            position 0;
                          }
                          ext:bit "ebgp" {
                            position 1;
                          }
                          ext:bit "network" {
                            position 2;
                          }
                          ext:bit "import" {
                            position 3;
                          }
                          ext:bit "auto-summary" {
                            position 4;
                          }
                          ext:bit "aggregate" {
                            position 5;
                          }
                          ext:bit "cpri" {
                            position 6;
                          }
                          ext:bit "pcri" {
                            position 7;
                          }
                          ext:bit "suppressed" {
                            position 8;
                          }
                          ext:bit "NHP-EMPTY" {
                            position 9;
                          }
                          ext:bit "NO-ADV" {
                            position 10;
                          }
                          ext:bit "local_cross" {
                            position 11;
                          }
                          ext:bit "remote_cross" {
                            position 12;
                          }
                          ext:bit "VD-BGP" {
                            position 13;
                          }
                          ext:bit "PATH_LOCAL" {
                            position 14;
                          }
                          ext:bit "PATH_GATEWAY" {
                            position 15;
                          }
                          ext:bit "policy_nopass" {
                            position 16;
                          }
                          ext:bit "supprenet" {
                            position 17;
                          }
                          ext:bit "dampened" {
                            position 18;
                          }
                          ext:bit "history" {
                            position 19;
                          }
                          ext:bit "select" {
                            position 20;
                          }
                          ext:bit "best" {
                            position 21;
                          }
                          ext:bit "backup" {
                            position 22;
                          }
                          ext:bit "attr_change" {
                            position 23;
                          }
                          ext:bit "NHLFE_CREATED" {
                            position 24;
                          }
                          ext:bit "ILM_CREATED" {
                            position 25;
                          }
                          ext:bit "NEXTHOP_CHANGE" {
                            position 26;
                          }
                          ext:bit "Invaild" {
                            position 27;
                          }
                          ext:bit "SOURCE_CHANGE" {
                            position 28;
                          }
                          ext:bit "IN_SELECTEDQ" {
                            position 29;
                          }
                          ext:bit "EXITIF_ERROR" {
                            position 30;
                          }
                          ext:bit "GROUP_HEAD" {
                            position 31;
                          }
                      }
                      config false;
                      description
                        "Route type.";
                    }
                    leaf imTableId {
                      type uint32 {
                        range "0..4294967295";
                      }
                      config false;
                      description
                        "ID of the routing table to which routes are imported.";
                    }
                    leaf rd {
                      type string {
                        length "1..22";
                      }
                      config false;
                      description
                        "Route distinguisher.";
                    }
                    leaf from {
                      type inet:ip-address-no-zone;
                      config false;
                      description
                        "Source peer that sends a route.";
                    }
                    leaf pathID {
                      type string {
                        length "1..50";
                      }
                      config false;
                      description
                        "Path ID.";
                    }
                    leaf remoteNextHopTunnelAddress {
                      type inet:ip-address-no-zone;
                      config false;
                      description
                        "The remote next hop tunnel address.";
                    }
                    leaf remoteNextHopMacAddress {
                      type pub-type:macAddress;
                      config false;
                      description
                        "The Remote next hop mac.";
                    }
                    leaf nexthop {
                      type inet:ip-address-no-zone;
                      config false;
                      description
                        "Next hop address to which packets are forwarded.";
                    }
                    leaf locPrf {
                      type uint32 {
                        range "0..4294967295";
                      }
                      config false;
                      description
                        "Local priority.The attribute is only fit for the routes from IBGP peer, not suit for which of EBGP peer.";
                    }
                    leaf prefVal {
                      type uint32 {
                        range "0..4294967295";
                      }
                      config false;
                      description
                        "Preferred value of a protocol.";
                    }
                    leaf prefrence {
                      type uint8 {
                        range "0..255";
                      }
                      config false;
                      description
                        "Priority of BGP routes.";
                    }
                    leaf pathAs {
                      type string {
                        length "1..300";
                      }
                      config false;
                      description
                        "List of the AS_Paths that packets pass through.";
                    }
                    leaf origin {
                      type bgpcommOrigin;
                      config false;
                      description
                        "Route origin.";
                    }
                    leaf med {
                      type uint32 {
                        range "0..4294967295";
                      }
                      config false;
                      description
                        "Route MED.The attribute is only fit for the routes from EBGP peer, not suit for which of IBGP peer.";
                    }
                    leaf flagString {
                      type string {
                        length "1..100";
                      }
                      config false;
                      description
                        "Route flag that contains a string of characters.";
                    }
                    leaf rtWorseReason {
                      type string {
                        length "1..50";
                      }
                      config false;
                      description
                        "Reason why a route is not selected.";
                    }
                    leaf peerString {
                      type string {
                        length "1..300";
                      }
                      config false;
                      description
                        "List of route sending peers.";
                    }
                    leaf time {
                      type uint32 {
                        range "0..4294967295";
                      }
                      config false;
                      description
                        "Time stamp of a route.";
                    }
                    leaf community {
                      type string {
                        length "1..120";
                      }
                      config false;
                      description
                        "Community attribute.";
                    }
                    leaf extCommunity {
                      type string {
                        length "1..300";
                      }
                      config false;
                      description
                        "Extended community attribute.";
                    }
                    leaf ifName {
                      type leafref {
                        path "/ifm:ifm/ifm:interfaces/ifm:interface/ifm:ifName";
                      }
                      config false;
                      description
                        "Name of the outbound interface of a route.";
                    }
                    leaf originator {
                      type inet:ip-address-no-zone;
                      config false;
                      description
                        "Router ID of the route initiator.";
                    }
                    leaf clusterList {
                      type string {
                        length "1..300";
                      }
                      config false;
                      description
                        "List of cluster IDs.";
                    }
                    leaf remoteRouteId {
                      type inet:ipv4-address-no-zone;
                      config false;
                      description
                        "Router ID of a peer.";
                    }
                    leaf relayNexthop {
                      type inet:ip-address-no-zone;
                      config false;
                      description
                        "Next hop to which a route is iterated.";
                    }
                    leaf relaytnlName {
                      type string {
                        length "1..64";
                      }
                      config false;
                      description
                        "Name of a tunnel to which a route is iterated.";
                    }
                    leaf isAtomicAggre {
                      type boolean;
                      default "false";
                      config false;
                      description
                        "Route carrying the atomic-aggregate attribute.";
                    }
                    leaf aggregatorAs {
                      type string {
                        length "1..11";
                      }
                      config false;
                      description
                        "AS number of the route summarizer.";
                    }
                    leaf aggregatorId {
                      type inet:ip-address-no-zone;
                      config false;
                      description
                        "ID of the route summarizer.";
                    }
                    leaf inLabel {
                      type uint32 {
                        range "0..4294967295";
                      }
                      config false;
                      description
                        "In-label.";
                    }
                    leaf outLabel {
                      type uint32 {
                        range "0..4294967295";
                      }
                      config false;
                      description
                        "Out-label.";
                    }
                    leaf disAttrString {
                      type string {
                        length "1..300";
                      }
                      config false;
                      description
                        "Discard the route attribute list.";
                    }
                    leaf vrfName {
                      type string {
                        length "1..31";
                      }
                      config false;
                      description
                        "Iterated Vrf .";
                    }
                    leaf remoteNextHopVni {
                      type uint32 {
                        range "0..4294967295";
                      }
                      config false;
                      description
                        "The remote next hop vni.";
                    }
                    leaf advNextHop {
                      type inet:ip-address-no-zone;
                      config false;
                      description
                        "Advertised Nexthop.";
                    }
                    leaf prefixSid {
                      type string {
                        length "1..60";
                      }
                      config false;
                      description
                        "PrefixSid attribute information of Route.";
                    }
                    leaf aigp {
                      type uint64;
                      config false;
                      description
                        "AIGP attribute information of Route.";
                    }
                    leaf attrSetString {
                      type string {
                        length "1..300";
                      }
                      config false;
                      description
                        "The attribute set information of Route.";
                    }
                  }
                }
                container peerNotAcceptRtTables {
                  config false;
                  description
                    "List of displayed route information in an address family.";
                  list peerNotAcceptRtTable {
                    when "not(../../../../afType!='ipv4uni' and ../../../../afType!='ipv4multi' and ../../../../afType!='ipv4vpn' and ../../../../afType!='ipv6uni' and ../../../../afType!='ipv6vpn')";
                    key "networkPrefix prefixMask routeTypeFlag imTableId rd from pathID";
                    config false;
                    description
                      "Information about routes.";
                    leaf networkPrefix {
                      type inet:ip-address-no-zone;
                      config false;
                      description
                        "BGP route prefix.";
                    }
                    leaf prefixMask {
                      type uint8;
                      config false;
                      description
                        "Prefix mask.";
                    }
                    leaf routeTypeFlag {
                      type pub-type:bits32 {
                        ext:masklen 32;
                          ext:bit "ibgp" {
                            position 0;
                          }
                          ext:bit "ebgp" {
                            position 1;
                          }
                          ext:bit "network" {
                            position 2;
                          }
                          ext:bit "import" {
                            position 3;
                          }
                          ext:bit "auto-summary" {
                            position 4;
                          }
                          ext:bit "aggregate" {
                            position 5;
                          }
                          ext:bit "cpri" {
                            position 6;
                          }
                          ext:bit "pcri" {
                            position 7;
                          }
                          ext:bit "suppressed" {
                            position 8;
                          }
                          ext:bit "NHP-EMPTY" {
                            position 9;
                          }
                          ext:bit "NO-ADV" {
                            position 10;
                          }
                          ext:bit "local_cross" {
                            position 11;
                          }
                          ext:bit "remote_cross" {
                            position 12;
                          }
                          ext:bit "VD-BGP" {
                            position 13;
                          }
                          ext:bit "PATH_LOCAL" {
                            position 14;
                          }
                          ext:bit "PATH_GATEWAY" {
                            position 15;
                          }
                          ext:bit "policy_nopass" {
                            position 16;
                          }
                          ext:bit "supprenet" {
                            position 17;
                          }
                          ext:bit "dampened" {
                            position 18;
                          }
                          ext:bit "history" {
                            position 19;
                          }
                          ext:bit "select" {
                            position 20;
                          }
                          ext:bit "best" {
                            position 21;
                          }
                          ext:bit "backup" {
                            position 22;
                          }
                          ext:bit "attr_change" {
                            position 23;
                          }
                          ext:bit "NHLFE_CREATED" {
                            position 24;
                          }
                          ext:bit "ILM_CREATED" {
                            position 25;
                          }
                          ext:bit "NEXTHOP_CHANGE" {
                            position 26;
                          }
                          ext:bit "Invaild" {
                            position 27;
                          }
                          ext:bit "SOURCE_CHANGE" {
                            position 28;
                          }
                          ext:bit "IN_SELECTEDQ" {
                            position 29;
                          }
                          ext:bit "EXITIF_ERROR" {
                            position 30;
                          }
                          ext:bit "GROUP_HEAD" {
                            position 31;
                          }
                      }
                      config false;
                      description
                        "Route type.";
                    }
                    leaf imTableId {
                      type uint32 {
                        range "0..4294967295";
                      }
                      config false;
                      description
                        "ID of the routing table to which routes are imported.";
                    }
                    leaf rd {
                      type string {
                        length "1..22";
                      }
                      config false;
                      description
                        "Route distinguisher.";
                    }
                    leaf from {
                      type inet:ip-address-no-zone;
                      config false;
                      description
                        "Source peer that sends a route.";
                    }
                    leaf pathID {
                      type string {
                        length "1..50";
                      }
                      config false;
                      description
                        "Path ID.";
                    }
                    leaf remoteNextHopTunnelAddress {
                      type inet:ip-address-no-zone;
                      config false;
                      description
                        "The remote next hop tunnel address.";
                    }
                    leaf remoteNextHopMacAddress {
                      type pub-type:macAddress;
                      config false;
                      description
                        "The Remote next hop mac.";
                    }
                    leaf nexthop {
                      type inet:ip-address-no-zone;
                      config false;
                      description
                        "Next hop address to which packets are forwarded.";
                    }
                    leaf locPrf {
                      type uint32 {
                        range "0..4294967295";
                      }
                      config false;
                      description
                        "Local priority.The attribute is only fit for the routes from IBGP peer, not suit for which of EBGP peer.";
                    }
                    leaf prefVal {
                      type uint32 {
                        range "0..4294967295";
                      }
                      config false;
                      description
                        "Preferred value of a protocol.";
                    }
                    leaf prefrence {
                      type uint8 {
                        range "0..255";
                      }
                      config false;
                      description
                        "Priority of BGP routes.";
                    }
                    leaf pathAs {
                      type string {
                        length "1..300";
                      }
                      config false;
                      description
                        "List of the AS_Paths that packets pass through.";
                    }
                    leaf origin {
                      type bgpcommOrigin;
                      config false;
                      description
                        "Route origin.";
                    }
                    leaf med {
                      type uint32 {
                        range "0..4294967295";
                      }
                      config false;
                      description
                        "Route MED.The attribute is only fit for the routes from EBGP peer, not suit for which of IBGP peer.";
                    }
                    leaf flagString {
                      type string {
                        length "1..100";
                      }
                      config false;
                      description
                        "Route flag that contains a string of characters.";
                    }
                    leaf rtWorseReason {
                      type string {
                        length "1..50";
                      }
                      config false;
                      description
                        "Reason why a route is not selected.";
                    }
                    leaf peerString {
                      type string {
                        length "1..300";
                      }
                      config false;
                      description
                        "List of route sending peers.";
                    }
                    leaf time {
                      type uint32 {
                        range "0..4294967295";
                      }
                      config false;
                      description
                        "Time stamp of a route.";
                    }
                    leaf community {
                      type string {
                        length "1..120";
                      }
                      config false;
                      description
                        "Community attribute.";
                    }
                    leaf extCommunity {
                      type string {
                        length "1..300";
                      }
                      config false;
                      description
                        "Extended community attribute.";
                    }
                    leaf ifName {
                      type leafref {
                        path "/ifm:ifm/ifm:interfaces/ifm:interface/ifm:ifName";
                      }
                      config false;
                      description
                        "Name of the outbound interface of a route.";
                    }
                    leaf originator {
                      type inet:ip-address-no-zone;
                      config false;
                      description
                        "Router ID of the route initiator.";
                    }
                    leaf clusterList {
                      type string {
                        length "1..300";
                      }
                      config false;
                      description
                        "List of cluster IDs.";
                    }
                    leaf remoteRouteId {
                      type inet:ipv4-address-no-zone;
                      config false;
                      description
                        "Router ID of a peer.";
                    }
                    leaf relayNexthop {
                      type inet:ip-address-no-zone;
                      config false;
                      description
                        "Next hop to which a route is iterated.";
                    }
                    leaf relaytnlName {
                      type string {
                        length "1..64";
                      }
                      config false;
                      description
                        "Name of a tunnel to which a route is iterated.";
                    }
                    leaf isAtomicAggre {
                      type boolean;
                      default "false";
                      config false;
                      description
                        "Route carrying the atomic-aggregate attribute.";
                    }
                    leaf aggregatorAs {
                      type string {
                        length "1..11";
                      }
                      config false;
                      description
                        "AS number of the route summarizer.";
                    }
                    leaf aggregatorId {
                      type inet:ip-address-no-zone;
                      config false;
                      description
                        "ID of the route summarizer.";
                    }
                    leaf inLabel {
                      type uint32 {
                        range "0..4294967295";
                      }
                      config false;
                      description
                        "In-label.";
                    }
                    leaf outLabel {
                      type uint32 {
                        range "0..4294967295";
                      }
                      config false;
                      description
                        "Out-label.";
                    }
                    leaf disAttrString {
                      type string {
                        length "1..300";
                      }
                      config false;
                      description
                        "Discard the route attribute list.";
                    }
                    leaf vrfName {
                      type string {
                        length "1..31";
                      }
                      config false;
                      description
                        "Iterated Vrf .";
                    }
                    leaf remoteNextHopVni {
                      type uint32 {
                        range "0..4294967295";
                      }
                      config false;
                      description
                        "The remote next hop vni.";
                    }
                    leaf advNextHop {
                      type inet:ip-address-no-zone;
                      config false;
                      description
                        "Advertised Nexthop.";
                    }
                    leaf prefixSid {
                      type string {
                        length "1..60";
                      }
                      config false;
                      description
                        "PrefixSid attribute information of Route.";
                    }
                    leaf aigp {
                      type uint64;
                      config false;
                      description
                        "AIGP attribute information of Route.";
                    }
                    leaf attrSetString {
                      type string {
                        length "1..300";
                      }
                      config false;
                      description
                        "The attribute set information of Route.";
                    }
                  }
                }
                container peerl2vpnAdRevRtTables {
                  config false;
                  description
                    "List of displayed BGP L2VPN-AD Rev route information.";
                  list peerl2vpnAdRevRtTable {
                    when "../../../../afType='l2vpnad'";
                    key "l2vpnAdNlri rd from routeTypeFlag imTableId";
                    config false;
                    description
                      "Information about BGP L2VPN-AD Rev routes.";
                    leaf l2vpnAdNlri {
                      type inet:ipv4-address-no-zone;
                      config false;
                      description
                        "Prefix of a BGP route.";
                    }
                    leaf rd {
                      type string {
                        length "1..22";
                      }
                      config false;
                      description
                        "Route distinguisher.";
                    }
                    leaf from {
                      type inet:ip-address-no-zone;
                      config false;
                      description
                        "Source peer that sends a route.";
                    }
                    leaf routeTypeFlag {
                      type pub-type:bits32 {
                        ext:masklen 32;
                          ext:bit "ibgp" {
                            position 0;
                          }
                          ext:bit "ebgp" {
                            position 1;
                          }
                          ext:bit "network" {
                            position 2;
                          }
                          ext:bit "import" {
                            position 3;
                          }
                          ext:bit "auto-summary" {
                            position 4;
                          }
                          ext:bit "aggregate" {
                            position 5;
                          }
                          ext:bit "cpri" {
                            position 6;
                          }
                          ext:bit "pcri" {
                            position 7;
                          }
                          ext:bit "suppressed" {
                            position 8;
                          }
                          ext:bit "NHP-EMPTY" {
                            position 9;
                          }
                          ext:bit "NO-ADV" {
                            position 10;
                          }
                          ext:bit "local_cross" {
                            position 11;
                          }
                          ext:bit "remote_cross" {
                            position 12;
                          }
                          ext:bit "VD-BGP" {
                            position 13;
                          }
                          ext:bit "PATH_LOCAL" {
                            position 14;
                          }
                          ext:bit "PATH_GATEWAY" {
                            position 15;
                          }
                          ext:bit "policy_nopass" {
                            position 16;
                          }
                          ext:bit "supprenet" {
                            position 17;
                          }
                          ext:bit "dampened" {
                            position 18;
                          }
                          ext:bit "history" {
                            position 19;
                          }
                          ext:bit "select" {
                            position 20;
                          }
                          ext:bit "best" {
                            position 21;
                          }
                          ext:bit "backup" {
                            position 22;
                          }
                          ext:bit "attr_change" {
                            position 23;
                          }
                          ext:bit "NHLFE_CREATED" {
                            position 24;
                          }
                          ext:bit "ILM_CREATED" {
                            position 25;
                          }
                          ext:bit "NEXTHOP_CHANGE" {
                            position 26;
                          }
                          ext:bit "Invaild" {
                            position 27;
                          }
                          ext:bit "SOURCE_CHANGE" {
                            position 28;
                          }
                          ext:bit "IN_SELECTEDQ" {
                            position 29;
                          }
                          ext:bit "EXITIF_ERROR" {
                            position 30;
                          }
                          ext:bit "GROUP_HEAD" {
                            position 31;
                          }
                      }
                      config false;
                      description
                        "Route type.";
                    }
                    leaf imTableId {
                      type uint32 {
                        range "0..4294967295";
                      }
                      config false;
                      description
                        "ID of the routing table to which routes are imported.";
                    }
                    leaf nexthop {
                      type inet:ip-address-no-zone;
                      config false;
                      description
                        "Next hop address to which packets are forwarded.";
                    }
                    leaf locPrf {
                      type uint32 {
                        range "0..4294967295";
                      }
                      config false;
                      description
                        "Local priority.The attribute is only fit for the routes from IBGP peer, not suit for which of EBGP peer.";
                    }
                    leaf prefVal {
                      type uint32 {
                        range "0..4294967295";
                      }
                      config false;
                      description
                        "Preferred value of a protocol.";
                    }
                    leaf prefrence {
                      type uint8 {
                        range "0..255";
                      }
                      config false;
                      description
                        "Priority of BGP routes.";
                    }
                    leaf pathAs {
                      type string {
                        length "1..300";
                      }
                      config false;
                      description
                        "List of the AS_Paths that packets pass through.";
                    }
                    leaf origin {
                      type bgpcommOrigin;
                      config false;
                      description
                        "Route origin.";
                    }
                    leaf med {
                      type uint32 {
                        range "0..4294967295";
                      }
                      config false;
                      description
                        "Route MED.The attribute is only fit for the routes from EBGP peer, not suit for which of IBGP peer.";
                    }
                    leaf flagString {
                      type string {
                        length "1..100";
                      }
                      config false;
                      description
                        "Route flag that contains a string of characters.";
                    }
                    leaf rtWorseReason {
                      type string {
                        length "1..50";
                      }
                      config false;
                      description
                        "Reason why a route is not selected.";
                    }
                    leaf peerString {
                      type string {
                        length "1..300";
                      }
                      config false;
                      description
                        "List of route sending peers.";
                    }
                    leaf time {
                      type uint32 {
                        range "0..4294967295";
                      }
                      config false;
                      description
                        "Time stamp of a route.";
                    }
                    leaf community {
                      type string {
                        length "1..120";
                      }
                      config false;
                      description
                        "Community attribute.";
                    }
                    leaf extCommunity {
                      type string {
                        length "1..300";
                      }
                      config false;
                      description
                        "Extended community attribute.";
                    }
                    leaf ifName {
                      type pub-type:ifName;
                      config false;
                      description
                        "Name of the outbound interface of a route.";
                    }
                    leaf originator {
                      type inet:ip-address-no-zone;
                      config false;
                      description
                        "Router ID of the route initiator.";
                    }
                    leaf clusterList {
                      type string {
                        length "1..300";
                      }
                      config false;
                      description
                        "List of cluster IDs.";
                    }
                    leaf remoteRouteId {
                      type inet:ipv4-address-no-zone;
                      config false;
                      description
                        "Router ID of a peer.";
                    }
                    leaf relayNexthop {
                      type inet:ip-address-no-zone;
                      config false;
                      description
                        "Next hop to which a route is iterated.";
                    }
                    leaf relaytnlName {
                      type string {
                        length "1..64";
                      }
                      config false;
                      description
                        "Name of a tunnel to which a route is iterated.";
                    }
                    leaf inLabel {
                      type uint32 {
                        range "0..4294967295";
                      }
                      config false;
                      description
                        "In-label.";
                    }
                    leaf outLabel {
                      type uint32 {
                        range "0..4294967295";
                      }
                      config false;
                      description
                        "Out-label.";
                    }
                    leaf pmsiString {
                      type string {
                        length "1..300";
                      }
                      config false;
                      description
                        "PMSI attribute.";
                    }
                    leaf advNextHop {
                      type inet:ip-address-no-zone;
                      config false;
                      description
                        "Next hop of an BGP.";
                    }
                  }
                }
                container peerl2vpnAdAdvRtTables {
                  config false;
                  description
                    "List of displayed BGP L2VPN-AD Adv route information.";
                  list peerl2vpnAdAdvRtTable {
                    when "../../../../afType='l2vpnad'";
                    key "l2vpnAdNlri rd from routeTypeFlag imTableId";
                    config false;
                    description
                      "Information about BGP L2VPN-AD Adv routes.";
                    leaf l2vpnAdNlri {
                      type inet:ipv4-address-no-zone;
                      config false;
                      description
                        "Prefix of a BGP route.";
                    }
                    leaf rd {
                      type string {
                        length "1..22";
                      }
                      config false;
                      description
                        "Route distinguisher.";
                    }
                    leaf from {
                      type inet:ip-address-no-zone;
                      config false;
                      description
                        "Source peer that sends a route.";
                    }
                    leaf routeTypeFlag {
                      type pub-type:bits32 {
                        ext:masklen 32;
                          ext:bit "ibgp" {
                            position 0;
                          }
                          ext:bit "ebgp" {
                            position 1;
                          }
                          ext:bit "network" {
                            position 2;
                          }
                          ext:bit "import" {
                            position 3;
                          }
                          ext:bit "auto-summary" {
                            position 4;
                          }
                          ext:bit "aggregate" {
                            position 5;
                          }
                          ext:bit "cpri" {
                            position 6;
                          }
                          ext:bit "pcri" {
                            position 7;
                          }
                          ext:bit "suppressed" {
                            position 8;
                          }
                          ext:bit "NHP-EMPTY" {
                            position 9;
                          }
                          ext:bit "NO-ADV" {
                            position 10;
                          }
                          ext:bit "local_cross" {
                            position 11;
                          }
                          ext:bit "remote_cross" {
                            position 12;
                          }
                          ext:bit "VD-BGP" {
                            position 13;
                          }
                          ext:bit "PATH_LOCAL" {
                            position 14;
                          }
                          ext:bit "PATH_GATEWAY" {
                            position 15;
                          }
                          ext:bit "policy_nopass" {
                            position 16;
                          }
                          ext:bit "supprenet" {
                            position 17;
                          }
                          ext:bit "dampened" {
                            position 18;
                          }
                          ext:bit "history" {
                            position 19;
                          }
                          ext:bit "select" {
                            position 20;
                          }
                          ext:bit "best" {
                            position 21;
                          }
                          ext:bit "backup" {
                            position 22;
                          }
                          ext:bit "attr_change" {
                            position 23;
                          }
                          ext:bit "NHLFE_CREATED" {
                            position 24;
                          }
                          ext:bit "ILM_CREATED" {
                            position 25;
                          }
                          ext:bit "NEXTHOP_CHANGE" {
                            position 26;
                          }
                          ext:bit "Invaild" {
                            position 27;
                          }
                          ext:bit "SOURCE_CHANGE" {
                            position 28;
                          }
                          ext:bit "IN_SELECTEDQ" {
                            position 29;
                          }
                          ext:bit "EXITIF_ERROR" {
                            position 30;
                          }
                          ext:bit "GROUP_HEAD" {
                            position 31;
                          }
                      }
                      config false;
                      description
                        "Route type.";
                    }
                    leaf imTableId {
                      type uint32 {
                        range "0..4294967295";
                      }
                      config false;
                      description
                        "ID of the routing table to which routes are imported.";
                    }
                    leaf nexthop {
                      type inet:ip-address-no-zone;
                      config false;
                      description
                        "Next hop address to which packets are forwarded.";
                    }
                    leaf locPrf {
                      type uint32 {
                        range "0..4294967295";
                      }
                      config false;
                      description
                        "Local priority.The attribute is only fit for the routes from IBGP peer, not suit for which of EBGP peer.";
                    }
                    leaf prefVal {
                      type uint32 {
                        range "0..4294967295";
                      }
                      config false;
                      description
                        "Preferred value of a protocol.";
                    }
                    leaf prefrence {
                      type uint8 {
                        range "0..255";
                      }
                      config false;
                      description
                        "Priority of BGP routes.";
                    }
                    leaf pathAs {
                      type string {
                        length "1..300";
                      }
                      config false;
                      description
                        "List of the AS_Paths that packets pass through.";
                    }
                    leaf origin {
                      type bgpcommOrigin;
                      config false;
                      description
                        "Route origin.";
                    }
                    leaf med {
                      type uint32 {
                        range "0..4294967295";
                      }
                      config false;
                      description
                        "Route MED.The attribute is only fit for the routes from EBGP peer, not suit for which of IBGP peer.";
                    }
                    leaf flagString {
                      type string {
                        length "1..100";
                      }
                      config false;
                      description
                        "Route flag that contains a string of characters.";
                    }
                    leaf rtWorseReason {
                      type string {
                        length "1..50";
                      }
                      config false;
                      description
                        "Reason why a route is not selected.";
                    }
                    leaf peerString {
                      type string {
                        length "1..300";
                      }
                      config false;
                      description
                        "List of route sending peers.";
                    }
                    leaf time {
                      type uint32 {
                        range "0..4294967295";
                      }
                      config false;
                      description
                        "Time stamp of a route.";
                    }
                    leaf community {
                      type string {
                        length "1..120";
                      }
                      config false;
                      description
                        "Community attribute.";
                    }
                    leaf extCommunity {
                      type string {
                        length "1..300";
                      }
                      config false;
                      description
                        "Extended community attribute.";
                    }
                    leaf ifName {
                      type pub-type:ifName;
                      config false;
                      description
                        "Name of the outbound interface of a route.";
                    }
                    leaf originator {
                      type inet:ip-address-no-zone;
                      config false;
                      description
                        "Router ID of the route initiator.";
                    }
                    leaf clusterList {
                      type string {
                        length "1..300";
                      }
                      config false;
                      description
                        "List of cluster IDs.";
                    }
                    leaf remoteRouteId {
                      type inet:ipv4-address-no-zone;
                      config false;
                      description
                        "Router ID of a peer.";
                    }
                    leaf relayNexthop {
                      type inet:ip-address-no-zone;
                      config false;
                      description
                        "Next hop to which a route is iterated.";
                    }
                    leaf relaytnlName {
                      type string {
                        length "1..64";
                      }
                      config false;
                      description
                        "Name of a tunnel to which a route is iterated.";
                    }
                    leaf inLabel {
                      type uint32 {
                        range "0..4294967295";
                      }
                      config false;
                      description
                        "In-label.";
                    }
                    leaf outLabel {
                      type uint32 {
                        range "0..4294967295";
                      }
                      config false;
                      description
                        "Out-label.";
                    }
                    leaf pmsiString {
                      type string {
                        length "1..300";
                      }
                      config false;
                      description
                        "PMSI attribute.";
                    }
                    leaf advNextHop {
                      type inet:ip-address-no-zone;
                      config false;
                      description
                        "Next hop of an BGP.";
                    }
                  }
                }
                container peerl2vpnAdRevActRtTables {
                  config false;
                  description
                    "List of displayed BGP L2VPN-AD Rev active route information.";
                  list peerl2vpnAdRevActRtTable {
                    when "../../../../afType='l2vpnad'";
                    key "l2vpnAdNlri rd from routeTypeFlag imTableId";
                    config false;
                    description
                      "Information about BGP L2VPN-AD Rev active routes.";
                    leaf l2vpnAdNlri {
                      type inet:ipv4-address-no-zone;
                      config false;
                      description
                        "Prefix of a BGP route.";
                    }
                    leaf rd {
                      type string {
                        length "1..22";
                      }
                      config false;
                      description
                        "Route distinguisher.";
                    }
                    leaf from {
                      type inet:ip-address-no-zone;
                      config false;
                      description
                        "Source peer that sends a route.";
                    }
                    leaf routeTypeFlag {
                      type pub-type:bits32 {
                        ext:masklen 32;
                          ext:bit "ibgp" {
                            position 0;
                          }
                          ext:bit "ebgp" {
                            position 1;
                          }
                          ext:bit "network" {
                            position 2;
                          }
                          ext:bit "import" {
                            position 3;
                          }
                          ext:bit "auto-summary" {
                            position 4;
                          }
                          ext:bit "aggregate" {
                            position 5;
                          }
                          ext:bit "cpri" {
                            position 6;
                          }
                          ext:bit "pcri" {
                            position 7;
                          }
                          ext:bit "suppressed" {
                            position 8;
                          }
                          ext:bit "NHP-EMPTY" {
                            position 9;
                          }
                          ext:bit "NO-ADV" {
                            position 10;
                          }
                          ext:bit "local_cross" {
                            position 11;
                          }
                          ext:bit "remote_cross" {
                            position 12;
                          }
                          ext:bit "VD-BGP" {
                            position 13;
                          }
                          ext:bit "PATH_LOCAL" {
                            position 14;
                          }
                          ext:bit "PATH_GATEWAY" {
                            position 15;
                          }
                          ext:bit "policy_nopass" {
                            position 16;
                          }
                          ext:bit "supprenet" {
                            position 17;
                          }
                          ext:bit "dampened" {
                            position 18;
                          }
                          ext:bit "history" {
                            position 19;
                          }
                          ext:bit "select" {
                            position 20;
                          }
                          ext:bit "best" {
                            position 21;
                          }
                          ext:bit "backup" {
                            position 22;
                          }
                          ext:bit "attr_change" {
                            position 23;
                          }
                          ext:bit "NHLFE_CREATED" {
                            position 24;
                          }
                          ext:bit "ILM_CREATED" {
                            position 25;
                          }
                          ext:bit "NEXTHOP_CHANGE" {
                            position 26;
                          }
                          ext:bit "Invaild" {
                            position 27;
                          }
                          ext:bit "SOURCE_CHANGE" {
                            position 28;
                          }
                          ext:bit "IN_SELECTEDQ" {
                            position 29;
                          }
                          ext:bit "EXITIF_ERROR" {
                            position 30;
                          }
                          ext:bit "GROUP_HEAD" {
                            position 31;
                          }
                      }
                      config false;
                      description
                        "Route type.";
                    }
                    leaf imTableId {
                      type uint32 {
                        range "0..4294967295";
                      }
                      config false;
                      description
                        "ID of the routing table to which routes are imported.";
                    }
                    leaf nexthop {
                      type inet:ip-address-no-zone;
                      config false;
                      description
                        "Next hop address to which packets are forwarded.";
                    }
                    leaf locPrf {
                      type uint32 {
                        range "0..4294967295";
                      }
                      config false;
                      description
                        "Local priority.The attribute is only fit for the routes from IBGP peer, not suit for which of EBGP peer.";
                    }
                    leaf prefVal {
                      type uint32 {
                        range "0..4294967295";
                      }
                      config false;
                      description
                        "Preferred value of a protocol.";
                    }
                    leaf prefrence {
                      type uint8 {
                        range "0..255";
                      }
                      config false;
                      description
                        "Priority of BGP routes.";
                    }
                    leaf pathAs {
                      type string {
                        length "1..300";
                      }
                      config false;
                      description
                        "List of the AS_Paths that packets pass through.";
                    }
                    leaf origin {
                      type bgpcommOrigin;
                      config false;
                      description
                        "Route origin.";
                    }
                    leaf med {
                      type uint32 {
                        range "0..4294967295";
                      }
                      config false;
                      description
                        "Route MED.The attribute is only fit for the routes from EBGP peer, not suit for which of IBGP peer.";
                    }
                    leaf flagString {
                      type string {
                        length "1..100";
                      }
                      config false;
                      description
                        "Route flag that contains a string of characters.";
                    }
                    leaf rtWorseReason {
                      type string {
                        length "1..50";
                      }
                      config false;
                      description
                        "Reason why a route is not selected.";
                    }
                    leaf peerString {
                      type string {
                        length "1..300";
                      }
                      config false;
                      description
                        "List of route sending peers.";
                    }
                    leaf time {
                      type uint32 {
                        range "0..4294967295";
                      }
                      config false;
                      description
                        "Time stamp of a route.";
                    }
                    leaf community {
                      type string {
                        length "1..120";
                      }
                      config false;
                      description
                        "Community attribute.";
                    }
                    leaf extCommunity {
                      type string {
                        length "1..300";
                      }
                      config false;
                      description
                        "Extended community attribute.";
                    }
                    leaf ifName {
                      type pub-type:ifName;
                      config false;
                      description
                        "Name of the outbound interface of a route.";
                    }
                    leaf originator {
                      type inet:ip-address-no-zone;
                      config false;
                      description
                        "Router ID of the route initiator.";
                    }
                    leaf clusterList {
                      type string {
                        length "1..300";
                      }
                      config false;
                      description
                        "List of cluster IDs.";
                    }
                    leaf remoteRouteId {
                      type inet:ipv4-address-no-zone;
                      config false;
                      description
                        "Router ID of a peer.";
                    }
                    leaf relayNexthop {
                      type inet:ip-address-no-zone;
                      config false;
                      description
                        "Next hop to which a route is iterated.";
                    }
                    leaf relaytnlName {
                      type string {
                        length "1..64";
                      }
                      config false;
                      description
                        "Name of a tunnel to which a route is iterated.";
                    }
                    leaf inLabel {
                      type uint32 {
                        range "0..4294967295";
                      }
                      config false;
                      description
                        "In-label.";
                    }
                    leaf outLabel {
                      type uint32 {
                        range "0..4294967295";
                      }
                      config false;
                      description
                        "Out-label.";
                    }
                    leaf pmsiString {
                      type string {
                        length "1..300";
                      }
                      config false;
                      description
                        "PMSI attribute.";
                    }
                    leaf advNextHop {
                      type inet:ip-address-no-zone;
                      config false;
                      description
                        "Next hop of an BGP.";
                    }
                  }
                }
                container peerVpnTargetRevRtTables {
                  config false;
                  description
                    "Information about VT routes in the VPN-TARGET address family.";
                  list peerVpnTargetRevRtTable {
                    when "../../../../afType='vpntarget'";
                    key "from routeTypeFlag imTableId rd";
                    config false;
                    description
                      "Information about VT routes in the VPN-TARGET address family.";
                    leaf from {
                      type inet:ip-address-no-zone;
                      config false;
                      description
                        "Source peer that sends a route.";
                    }
                    leaf routeTypeFlag {
                      type pub-type:bits32 {
                        ext:masklen 32;
                          ext:bit "ibgp" {
                            position 0;
                          }
                          ext:bit "ebgp" {
                            position 1;
                          }
                          ext:bit "network" {
                            position 2;
                          }
                          ext:bit "import" {
                            position 3;
                          }
                          ext:bit "auto-summary" {
                            position 4;
                          }
                          ext:bit "aggregate" {
                            position 5;
                          }
                          ext:bit "cpri" {
                            position 6;
                          }
                          ext:bit "pcri" {
                            position 7;
                          }
                          ext:bit "suppressed" {
                            position 8;
                          }
                          ext:bit "NHP-EMPTY" {
                            position 9;
                          }
                          ext:bit "NO-ADV" {
                            position 10;
                          }
                          ext:bit "local_cross" {
                            position 11;
                          }
                          ext:bit "remote_cross" {
                            position 12;
                          }
                          ext:bit "VD-BGP" {
                            position 13;
                          }
                          ext:bit "PATH_LOCAL" {
                            position 14;
                          }
                          ext:bit "PATH_GATEWAY" {
                            position 15;
                          }
                          ext:bit "policy_nopass" {
                            position 16;
                          }
                          ext:bit "supprenet" {
                            position 17;
                          }
                          ext:bit "dampened" {
                            position 18;
                          }
                          ext:bit "history" {
                            position 19;
                          }
                          ext:bit "select" {
                            position 20;
                          }
                          ext:bit "best" {
                            position 21;
                          }
                          ext:bit "backup" {
                            position 22;
                          }
                          ext:bit "attr_change" {
                            position 23;
                          }
                          ext:bit "NHLFE_CREATED" {
                            position 24;
                          }
                          ext:bit "ILM_CREATED" {
                            position 25;
                          }
                          ext:bit "NEXTHOP_CHANGE" {
                            position 26;
                          }
                          ext:bit "Invaild" {
                            position 27;
                          }
                          ext:bit "SOURCE_CHANGE" {
                            position 28;
                          }
                          ext:bit "IN_SELECTEDQ" {
                            position 29;
                          }
                          ext:bit "EXITIF_ERROR" {
                            position 30;
                          }
                          ext:bit "GROUP_HEAD" {
                            position 31;
                          }
                      }
                      config false;
                      description
                        "Route type.";
                    }
                    leaf imTableId {
                      type uint32 {
                        range "0..4294967295";
                      }
                      config false;
                      description
                        "ID of the routing table to which routes are imported.";
                    }
                    leaf rd {
                      type string {
                        length "1..22";
                      }
                      config false;
                      description
                        "Route distinguisher.";
                    }
                    leaf vtPrefix {
                      type string {
                        length "1..50";
                      }
                      config false;
                      description
                        "Prefix of a BGP route.";
                    }
                    leaf originAs {
                      type string {
                        length "1..50";
                      }
                      config false;
                      description
                        "Origin-As.";
                    }
                    leaf nexthop {
                      type inet:ip-address-no-zone;
                      config false;
                      description
                        "Next hop address to which packets are forwarded.";
                    }
                    leaf locPrf {
                      type uint32 {
                        range "0..4294967295";
                      }
                      config false;
                      description
                        "Local priority.The attribute is only fit for the routes from IBGP peer, not suit for which of EBGP peer.";
                    }
                    leaf prefVal {
                      type uint32 {
                        range "0..4294967295";
                      }
                      config false;
                      description
                        "Preferred value of a protocol.";
                    }
                    leaf prefrence {
                      type uint8 {
                        range "0..255";
                      }
                      config false;
                      description
                        "Priority of BGP routes.";
                    }
                    leaf pathAs {
                      type string {
                        length "1..300";
                      }
                      config false;
                      description
                        "List of the AS_Paths that packets pass through.";
                    }
                    leaf origin {
                      type bgpcommOrigin;
                      config false;
                      description
                        "Route origin.";
                    }
                    leaf med {
                      type uint32 {
                        range "0..4294967295";
                      }
                      config false;
                      description
                        "Route MED.The attribute is only fit for the routes from EBGP peer, not suit for which of IBGP peer.";
                    }
                    leaf flagString {
                      type string {
                        length "1..100";
                      }
                      config false;
                      description
                        "Route flag that contains a string of characters.";
                    }
                    leaf rtWorseReason {
                      type string {
                        length "1..50";
                      }
                      config false;
                      description
                        "Reason why a route is not selected.";
                    }
                    leaf peerString {
                      type string {
                        length "1..300";
                      }
                      config false;
                      description
                        "List of route sending peers.";
                    }
                    leaf time {
                      type uint32 {
                        range "0..4294967295";
                      }
                      config false;
                      description
                        "Time stamp of a route.";
                    }
                    leaf community {
                      type string {
                        length "1..120";
                      }
                      config false;
                      description
                        "Community attribute.";
                    }
                    leaf extCommunity {
                      type string {
                        length "1..300";
                      }
                      config false;
                      description
                        "Extended community attribute.";
                    }
                    leaf ifName {
                      type pub-type:ifName;
                      config false;
                      description
                        "Name of the outbound interface of a route.";
                    }
                    leaf originator {
                      type inet:ip-address-no-zone;
                      config false;
                      description
                        "Router ID of the route initiator.";
                    }
                    leaf clusterList {
                      type string {
                        length "1..300";
                      }
                      config false;
                      description
                        "List of cluster IDs.";
                    }
                    leaf remoteRouteId {
                      type inet:ipv4-address-no-zone;
                      config false;
                      description
                        "Router ID of a peer.";
                    }
                    leaf relayNexthop {
                      type inet:ip-address-no-zone;
                      config false;
                      description
                        "Next hop to which a route is iterated.";
                    }
                    leaf advNextHop {
                      type inet:ip-address-no-zone;
                      config false;
                      description
                        "Next hop of an BGP.";
                    }
                  }
                }
                container peerVpnTargetAdvRtTables {
                  config false;
                  description
                    "Information about VT routes in the VPN-TARGET address family.";
                  list peerVpnTargetAdvRtTable {
                    when "../../../../afType='vpntarget'";
                    key "from routeTypeFlag imTableId rd";
                    config false;
                    description
                      "Information about VT routes in the VPN-TARGET address family.";
                    leaf from {
                      type inet:ip-address-no-zone;
                      config false;
                      description
                        "Source peer that sends a route.";
                    }
                    leaf routeTypeFlag {
                      type pub-type:bits32 {
                        ext:masklen 32;
                          ext:bit "ibgp" {
                            position 0;
                          }
                          ext:bit "ebgp" {
                            position 1;
                          }
                          ext:bit "network" {
                            position 2;
                          }
                          ext:bit "import" {
                            position 3;
                          }
                          ext:bit "auto-summary" {
                            position 4;
                          }
                          ext:bit "aggregate" {
                            position 5;
                          }
                          ext:bit "cpri" {
                            position 6;
                          }
                          ext:bit "pcri" {
                            position 7;
                          }
                          ext:bit "suppressed" {
                            position 8;
                          }
                          ext:bit "NHP-EMPTY" {
                            position 9;
                          }
                          ext:bit "NO-ADV" {
                            position 10;
                          }
                          ext:bit "local_cross" {
                            position 11;
                          }
                          ext:bit "remote_cross" {
                            position 12;
                          }
                          ext:bit "VD-BGP" {
                            position 13;
                          }
                          ext:bit "PATH_LOCAL" {
                            position 14;
                          }
                          ext:bit "PATH_GATEWAY" {
                            position 15;
                          }
                          ext:bit "policy_nopass" {
                            position 16;
                          }
                          ext:bit "supprenet" {
                            position 17;
                          }
                          ext:bit "dampened" {
                            position 18;
                          }
                          ext:bit "history" {
                            position 19;
                          }
                          ext:bit "select" {
                            position 20;
                          }
                          ext:bit "best" {
                            position 21;
                          }
                          ext:bit "backup" {
                            position 22;
                          }
                          ext:bit "attr_change" {
                            position 23;
                          }
                          ext:bit "NHLFE_CREATED" {
                            position 24;
                          }
                          ext:bit "ILM_CREATED" {
                            position 25;
                          }
                          ext:bit "NEXTHOP_CHANGE" {
                            position 26;
                          }
                          ext:bit "Invaild" {
                            position 27;
                          }
                          ext:bit "SOURCE_CHANGE" {
                            position 28;
                          }
                          ext:bit "IN_SELECTEDQ" {
                            position 29;
                          }
                          ext:bit "EXITIF_ERROR" {
                            position 30;
                          }
                          ext:bit "GROUP_HEAD" {
                            position 31;
                          }
                      }
                      config false;
                      description
                        "Route type.";
                    }
                    leaf imTableId {
                      type uint32 {
                        range "0..4294967295";
                      }
                      config false;
                      description
                        "ID of the routing table to which routes are imported.";
                    }
                    leaf rd {
                      type string {
                        length "1..22";
                      }
                      config false;
                      description
                        "Route distinguisher.";
                    }
                    leaf vtPrefix {
                      type string {
                        length "1..50";
                      }
                      config false;
                      description
                        "Prefix of a BGP route.";
                    }
                    leaf originAs {
                      type string {
                        length "1..50";
                      }
                      config false;
                      description
                        "Origin-As.";
                    }
                    leaf nexthop {
                      type inet:ip-address-no-zone;
                      config false;
                      description
                        "Next hop address to which packets are forwarded.";
                    }
                    leaf locPrf {
                      type uint32 {
                        range "0..4294967295";
                      }
                      config false;
                      description
                        "Local priority.The attribute is only fit for the routes from IBGP peer, not suit for which of EBGP peer.";
                    }
                    leaf prefVal {
                      type uint32 {
                        range "0..4294967295";
                      }
                      config false;
                      description
                        "Preferred value of a protocol.";
                    }
                    leaf prefrence {
                      type uint8 {
                        range "0..255";
                      }
                      config false;
                      description
                        "Priority of BGP routes.";
                    }
                    leaf pathAs {
                      type string {
                        length "1..300";
                      }
                      config false;
                      description
                        "List of the AS_Paths that packets pass through.";
                    }
                    leaf origin {
                      type bgpcommOrigin;
                      config false;
                      description
                        "Route origin.";
                    }
                    leaf med {
                      type uint32 {
                        range "0..4294967295";
                      }
                      config false;
                      description
                        "Route MED.The attribute is only fit for the routes from EBGP peer, not suit for which of IBGP peer.";
                    }
                    leaf flagString {
                      type string {
                        length "1..100";
                      }
                      config false;
                      description
                        "Route flag that contains a string of characters.";
                    }
                    leaf rtWorseReason {
                      type string {
                        length "1..50";
                      }
                      config false;
                      description
                        "Reason why a route is not selected.";
                    }
                    leaf peerString {
                      type string {
                        length "1..300";
                      }
                      config false;
                      description
                        "List of route sending peers.";
                    }
                    leaf time {
                      type uint32 {
                        range "0..4294967295";
                      }
                      config false;
                      description
                        "Time stamp of a route.";
                    }
                    leaf community {
                      type string {
                        length "1..120";
                      }
                      config false;
                      description
                        "Community attribute.";
                    }
                    leaf extCommunity {
                      type string {
                        length "1..300";
                      }
                      config false;
                      description
                        "Extended community attribute.";
                    }
                    leaf ifName {
                      type pub-type:ifName;
                      config false;
                      description
                        "Name of the outbound interface of a route.";
                    }
                    leaf originator {
                      type inet:ip-address-no-zone;
                      config false;
                      description
                        "Router ID of the route initiator.";
                    }
                    leaf clusterList {
                      type string {
                        length "1..300";
                      }
                      config false;
                      description
                        "List of cluster IDs.";
                    }
                    leaf remoteRouteId {
                      type inet:ipv4-address-no-zone;
                      config false;
                      description
                        "Router ID of a peer.";
                    }
                    leaf relayNexthop {
                      type inet:ip-address-no-zone;
                      config false;
                      description
                        "Next hop to which a route is iterated.";
                    }
                    leaf advNextHop {
                      type inet:ip-address-no-zone;
                      config false;
                      description
                        "Next hop of an BGP.";
                    }
                  }
                }
                container peerIpv4MdtRevRtTables {
                  config false;
                  description
                    "List of displayed route information in MDT Rev address family.";
                  list peerIpv4MdtRevRtTable {
                    when "../../../../afType='mdt'";
                    key "from networkPrefix prefixMask mdtGroupAddr rd routeTypeFlag imTableId";
                    config false;
                    description
                      "Information about MDT Rev routes.";
                    leaf from {
                      type inet:ip-address-no-zone;
                      config false;
                      description
                        "Source peer that sends a route.";
                    }
                    leaf networkPrefix {
                      type inet:ip-address-no-zone;
                      config false;
                      description
                        "BGP route prefix.";
                    }
                    leaf prefixMask {
                      type uint8;
                      config false;
                      description
                        "Prefix mask.";
                    }
                    leaf mdtGroupAddr {
                      type inet:ip-address-no-zone;
                      config false;
                      description
                        "MDT Group Address.";
                    }
                    leaf rd {
                      type string {
                        length "1..22";
                      }
                      config false;
                      description
                        "Route distinguisher.";
                    }
                    leaf routeTypeFlag {
                      type pub-type:bits32 {
                        ext:masklen 32;
                          ext:bit "ibgp" {
                            position 0;
                          }
                          ext:bit "ebgp" {
                            position 1;
                          }
                          ext:bit "network" {
                            position 2;
                          }
                          ext:bit "import" {
                            position 3;
                          }
                          ext:bit "auto-summary" {
                            position 4;
                          }
                          ext:bit "aggregate" {
                            position 5;
                          }
                          ext:bit "cpri" {
                            position 6;
                          }
                          ext:bit "pcri" {
                            position 7;
                          }
                          ext:bit "suppressed" {
                            position 8;
                          }
                          ext:bit "NHP-EMPTY" {
                            position 9;
                          }
                          ext:bit "NO-ADV" {
                            position 10;
                          }
                          ext:bit "local_cross" {
                            position 11;
                          }
                          ext:bit "remote_cross" {
                            position 12;
                          }
                          ext:bit "VD-BGP" {
                            position 13;
                          }
                          ext:bit "PATH_LOCAL" {
                            position 14;
                          }
                          ext:bit "PATH_GATEWAY" {
                            position 15;
                          }
                          ext:bit "policy_nopass" {
                            position 16;
                          }
                          ext:bit "supprenet" {
                            position 17;
                          }
                          ext:bit "dampened" {
                            position 18;
                          }
                          ext:bit "history" {
                            position 19;
                          }
                          ext:bit "select" {
                            position 20;
                          }
                          ext:bit "best" {
                            position 21;
                          }
                          ext:bit "backup" {
                            position 22;
                          }
                          ext:bit "attr_change" {
                            position 23;
                          }
                          ext:bit "NHLFE_CREATED" {
                            position 24;
                          }
                          ext:bit "ILM_CREATED" {
                            position 25;
                          }
                          ext:bit "NEXTHOP_CHANGE" {
                            position 26;
                          }
                          ext:bit "Invaild" {
                            position 27;
                          }
                          ext:bit "SOURCE_CHANGE" {
                            position 28;
                          }
                          ext:bit "IN_SELECTEDQ" {
                            position 29;
                          }
                          ext:bit "EXITIF_ERROR" {
                            position 30;
                          }
                          ext:bit "GROUP_HEAD" {
                            position 31;
                          }
                      }
                      config false;
                      description
                        "Route type.";
                    }
                    leaf imTableId {
                      type uint32 {
                        range "0..4294967295";
                      }
                      config false;
                      description
                        "ID of the routing table to which routes are imported.";
                    }
                    leaf nexthop {
                      type inet:ip-address-no-zone;
                      config false;
                      description
                        "Next hop address to which packets are forwarded.";
                    }
                    leaf locPrf {
                      type uint32 {
                        range "0..4294967295";
                      }
                      config false;
                      description
                        "Local priority.The attribute is only fit for the routes from IBGP peer, not suit for which of EBGP peer.";
                    }
                    leaf prefVal {
                      type uint32 {
                        range "0..4294967295";
                      }
                      config false;
                      description
                        "Preferred value of a protocol.";
                    }
                    leaf prefrence {
                      type uint8 {
                        range "0..255";
                      }
                      config false;
                      description
                        "Priority of BGP routes.";
                    }
                    leaf pathAs {
                      type string {
                        length "1..300";
                      }
                      config false;
                      description
                        "List of the AS_Paths that packets pass through.";
                    }
                    leaf origin {
                      type bgpcommOrigin;
                      config false;
                      description
                        "Route origin.";
                    }
                    leaf med {
                      type uint32 {
                        range "0..4294967295";
                      }
                      config false;
                      description
                        "Route MED.The attribute is only fit for the routes from EBGP peer, not suit for which of IBGP peer.";
                    }
                    leaf flagString {
                      type string {
                        length "1..100";
                      }
                      config false;
                      description
                        "Route flag that contains a string of characters.";
                    }
                    leaf rtWorseReason {
                      type string {
                        length "1..50";
                      }
                      config false;
                      description
                        "Reason why a route is not selected.";
                    }
                    leaf peerString {
                      type string {
                        length "1..300";
                      }
                      config false;
                      description
                        "List of route sending peers.";
                    }
                    leaf time {
                      type uint32 {
                        range "0..4294967295";
                      }
                      config false;
                      description
                        "Time stamp of a route.";
                    }
                    leaf community {
                      type string {
                        length "1..120";
                      }
                      config false;
                      description
                        "Community attribute.";
                    }
                    leaf extCommunity {
                      type string {
                        length "1..300";
                      }
                      config false;
                      description
                        "Extended community attribute.";
                    }
                    leaf ifName {
                      type pub-type:ifName;
                      config false;
                      description
                        "Name of the outbound interface of a route.";
                    }
                    leaf originator {
                      type inet:ip-address-no-zone;
                      config false;
                      description
                        "Router ID of the route initiator.";
                    }
                    leaf clusterList {
                      type string {
                        length "1..300";
                      }
                      config false;
                      description
                        "List of cluster IDs.";
                    }
                    leaf remoteRouteId {
                      type inet:ipv4-address-no-zone;
                      config false;
                      description
                        "Router ID of a peer.";
                    }
                    leaf relayNexthop {
                      type inet:ip-address-no-zone;
                      config false;
                      description
                        "Next hop to which a route is iterated.";
                    }
                    leaf relaytnlName {
                      type string {
                        length "1..64";
                      }
                      config false;
                      description
                        "Name of a tunnel to which a route is iterated.";
                    }
                    leaf inLabel {
                      type uint32 {
                        range "0..4294967295";
                      }
                      config false;
                      description
                        "In-label.";
                    }
                    leaf outLabel {
                      type uint32 {
                        range "0..4294967295";
                      }
                      config false;
                      description
                        "Out-label.";
                    }
                    leaf advNextHop {
                      type inet:ip-address-no-zone;
                      config false;
                      description
                        "Next hop of an BGP.";
                    }
                  }
                }
                container peerIpv4MdtAdvRtTables {
                  config false;
                  description
                    "List of displayed route information in MDT adv address family.";
                  list peerIpv4MdtAdvRtTable {
                    when "../../../../afType='mdt'";
                    key "from networkPrefix prefixMask mdtGroupAddr rd routeTypeFlag imTableId";
                    config false;
                    description
                      "Information about MDT Adv routes.";
                    leaf from {
                      type inet:ip-address-no-zone;
                      config false;
                      description
                        "Source peer that sends a route.";
                    }
                    leaf networkPrefix {
                      type inet:ip-address-no-zone;
                      config false;
                      description
                        "BGP route prefix.";
                    }
                    leaf prefixMask {
                      type uint8;
                      config false;
                      description
                        "Prefix mask.";
                    }
                    leaf mdtGroupAddr {
                      type inet:ip-address-no-zone;
                      config false;
                      description
                        "MDT Group Address.";
                    }
                    leaf rd {
                      type string {
                        length "1..22";
                      }
                      config false;
                      description
                        "Route distinguisher.";
                    }
                    leaf routeTypeFlag {
                      type pub-type:bits32 {
                        ext:masklen 32;
                          ext:bit "ibgp" {
                            position 0;
                          }
                          ext:bit "ebgp" {
                            position 1;
                          }
                          ext:bit "network" {
                            position 2;
                          }
                          ext:bit "import" {
                            position 3;
                          }
                          ext:bit "auto-summary" {
                            position 4;
                          }
                          ext:bit "aggregate" {
                            position 5;
                          }
                          ext:bit "cpri" {
                            position 6;
                          }
                          ext:bit "pcri" {
                            position 7;
                          }
                          ext:bit "suppressed" {
                            position 8;
                          }
                          ext:bit "NHP-EMPTY" {
                            position 9;
                          }
                          ext:bit "NO-ADV" {
                            position 10;
                          }
                          ext:bit "local_cross" {
                            position 11;
                          }
                          ext:bit "remote_cross" {
                            position 12;
                          }
                          ext:bit "VD-BGP" {
                            position 13;
                          }
                          ext:bit "PATH_LOCAL" {
                            position 14;
                          }
                          ext:bit "PATH_GATEWAY" {
                            position 15;
                          }
                          ext:bit "policy_nopass" {
                            position 16;
                          }
                          ext:bit "supprenet" {
                            position 17;
                          }
                          ext:bit "dampened" {
                            position 18;
                          }
                          ext:bit "history" {
                            position 19;
                          }
                          ext:bit "select" {
                            position 20;
                          }
                          ext:bit "best" {
                            position 21;
                          }
                          ext:bit "backup" {
                            position 22;
                          }
                          ext:bit "attr_change" {
                            position 23;
                          }
                          ext:bit "NHLFE_CREATED" {
                            position 24;
                          }
                          ext:bit "ILM_CREATED" {
                            position 25;
                          }
                          ext:bit "NEXTHOP_CHANGE" {
                            position 26;
                          }
                          ext:bit "Invaild" {
                            position 27;
                          }
                          ext:bit "SOURCE_CHANGE" {
                            position 28;
                          }
                          ext:bit "IN_SELECTEDQ" {
                            position 29;
                          }
                          ext:bit "EXITIF_ERROR" {
                            position 30;
                          }
                          ext:bit "GROUP_HEAD" {
                            position 31;
                          }
                      }
                      config false;
                      description
                        "Route type.";
                    }
                    leaf imTableId {
                      type uint32 {
                        range "0..4294967295";
                      }
                      config false;
                      description
                        "ID of the routing table to which routes are imported.";
                    }
                    leaf nexthop {
                      type inet:ip-address-no-zone;
                      config false;
                      description
                        "Next hop address to which packets are forwarded.";
                    }
                    leaf locPrf {
                      type uint32 {
                        range "0..4294967295";
                      }
                      config false;
                      description
                        "Local priority.The attribute is only fit for the routes from IBGP peer, not suit for which of EBGP peer.";
                    }
                    leaf prefVal {
                      type uint32 {
                        range "0..4294967295";
                      }
                      config false;
                      description
                        "Preferred value of a protocol.";
                    }
                    leaf prefrence {
                      type uint8 {
                        range "0..255";
                      }
                      config false;
                      description
                        "Priority of BGP routes.";
                    }
                    leaf pathAs {
                      type string {
                        length "1..300";
                      }
                      config false;
                      description
                        "List of the AS_Paths that packets pass through.";
                    }
                    leaf origin {
                      type bgpcommOrigin;
                      config false;
                      description
                        "Route origin.";
                    }
                    leaf med {
                      type uint32 {
                        range "0..4294967295";
                      }
                      config false;
                      description
                        "Route MED.The attribute is only fit for the routes from EBGP peer, not suit for which of IBGP peer.";
                    }
                    leaf flagString {
                      type string {
                        length "1..100";
                      }
                      config false;
                      description
                        "Route flag that contains a string of characters.";
                    }
                    leaf rtWorseReason {
                      type string {
                        length "1..50";
                      }
                      config false;
                      description
                        "Reason why a route is not selected.";
                    }
                    leaf peerString {
                      type string {
                        length "1..300";
                      }
                      config false;
                      description
                        "List of route sending peers.";
                    }
                    leaf time {
                      type uint32 {
                        range "0..4294967295";
                      }
                      config false;
                      description
                        "Time stamp of a route.";
                    }
                    leaf community {
                      type string {
                        length "1..120";
                      }
                      config false;
                      description
                        "Community attribute.";
                    }
                    leaf extCommunity {
                      type string {
                        length "1..300";
                      }
                      config false;
                      description
                        "Extended community attribute.";
                    }
                    leaf ifName {
                      type pub-type:ifName;
                      config false;
                      description
                        "Name of the outbound interface of a route.";
                    }
                    leaf originator {
                      type inet:ip-address-no-zone;
                      config false;
                      description
                        "Router ID of the route initiator.";
                    }
                    leaf clusterList {
                      type string {
                        length "1..300";
                      }
                      config false;
                      description
                        "List of cluster IDs.";
                    }
                    leaf remoteRouteId {
                      type inet:ipv4-address-no-zone;
                      config false;
                      description
                        "Router ID of a peer.";
                    }
                    leaf relayNexthop {
                      type inet:ip-address-no-zone;
                      config false;
                      description
                        "Next hop to which a route is iterated.";
                    }
                    leaf relaytnlName {
                      type string {
                        length "1..64";
                      }
                      config false;
                      description
                        "Name of a tunnel to which a route is iterated.";
                    }
                    leaf inLabel {
                      type uint32 {
                        range "0..4294967295";
                      }
                      config false;
                      description
                        "In-label.";
                    }
                    leaf outLabel {
                      type uint32 {
                        range "0..4294967295";
                      }
                      config false;
                      description
                        "Out-label.";
                    }
                    leaf advNextHop {
                      type inet:ip-address-no-zone;
                      config false;
                      description
                        "Next hop of an BGP.";
                    }
                  }
                }
                container peerNgRevRtTable1s {
                  config false;
                  description
                    "List of displayed BGP Ng Rev route type 1 information.";
                  list peerNgRevRtTable1 {
                    when "not(../../../../afType!='mvpn' and ../../../../afType!='mvpnv6')";
                    key "ngNlri rd from ngRouteType routeTypeFlag";
                    config false;
                    description
                      "Information about BGP Ng Rev routes type 1.";
                    leaf ngNlri {
                      type inet:ipv4-address-no-zone;
                      config false;
                      description
                        "Prefix of a BGP route.";
                    }
                    leaf imTableId {
                      type uint32 {
                        range "0..4294967295";
                      }
                      config false;
                      description
                        "ID of the routing table to which routes are imported.";
                    }
                    leaf nexthop {
                      type inet:ip-address-no-zone;
                      config false;
                      description
                        "Next hop address to which packets are forwarded.";
                    }
                    leaf locPrf {
                      type uint32 {
                        range "0..4294967295";
                      }
                      config false;
                      description
                        "Local-preference.";
                    }
                    leaf prefVal {
                      type uint32 {
                        range "0..4294967295";
                      }
                      config false;
                      description
                        "Preferred value of a protocol.";
                    }
                    leaf prefrence {
                      type uint8 {
                        range "0..255";
                      }
                      config false;
                      description
                        "Priority of BGP routes.";
                    }
                    leaf pathAs {
                      type string {
                        length "1..300";
                      }
                      config false;
                      description
                        "List of the AS_Paths that packets pass through.";
                    }
                    leaf origin {
                      type bgpcommOrigin;
                      config false;
                      description
                        "Route origin.";
                    }
                    leaf med {
                      type uint32 {
                        range "0..4294967295";
                      }
                      config false;
                      description
                        "Route MED.";
                    }
                    leaf flagString {
                      type string {
                        length "1..100";
                      }
                      config false;
                      description
                        "Route flag that contains a string of characters.";
                    }
                    leaf rd {
                      type string {
                        length "1..22";
                      }
                      config false;
                      description
                        "Route distinguisher.";
                    }
                    leaf rtWorseReason {
                      type string {
                        length "1..50";
                      }
                      config false;
                      description
                        "Reason why a route is not selected.";
                    }
                    leaf peerString {
                      type string {
                        length "1..300";
                      }
                      config false;
                      description
                        "List of route sending peers.";
                    }
                    leaf time {
                      type uint32 {
                        range "0..4294967295";
                      }
                      config false;
                      description
                        "Time stamp of a route.";
                    }
                    leaf community {
                      type string {
                        length "1..120";
                      }
                      config false;
                      description
                        "Community attribute.";
                    }
                    leaf extCommunity {
                      type string {
                        length "1..300";
                      }
                      config false;
                      description
                        "Extended community attribute.";
                    }
                    leaf from {
                      type inet:ip-address-no-zone;
                      config false;
                      description
                        "Source peer that sends a route.";
                    }
                    leaf ifName {
                      type pub-type:ifName;
                      config false;
                      description
                        "Name of the outbound interface of a route.";
                    }
                    leaf originator {
                      type inet:ip-address-no-zone;
                      config false;
                      description
                        "Router ID of the route initiator.";
                    }
                    leaf clusterList {
                      type string {
                        length "1..300";
                      }
                      config false;
                      description
                        "List of cluster IDs.";
                    }
                    leaf remoteRouteId {
                      type inet:ipv4-address-no-zone;
                      config false;
                      description
                        "Router ID of a peer.";
                    }
                    leaf relayNexthop {
                      type inet:ip-address-no-zone;
                      config false;
                      description
                        "Next hop to which a route is iterated.";
                    }
                    leaf relaytnlName {
                      type string {
                        length "1..64";
                      }
                      config false;
                      description
                        "Name of a tunnel to which a route is iterated.";
                    }
                    leaf inLabel {
                      type uint32 {
                        range "0..4294967295";
                      }
                      config false;
                      description
                        "In-label.";
                    }
                    leaf outLabel {
                      type uint32 {
                        range "0..4294967295";
                      }
                      config false;
                      description
                        "Out-label.";
                    }
                    leaf ngRouteType {
                      type string {
                        length "1..50";
                      }
                      config false;
                      description
                        "Route type.";
                    }
                    leaf routeTypeFlag {
                      type pub-type:bits32 {
                        ext:masklen 32;
                          ext:bit "ibgp" {
                            position 0;
                          }
                          ext:bit "ebgp" {
                            position 1;
                          }
                          ext:bit "network" {
                            position 2;
                          }
                          ext:bit "import" {
                            position 3;
                          }
                          ext:bit "auto-summary" {
                            position 4;
                          }
                          ext:bit "aggregate" {
                            position 5;
                          }
                          ext:bit "cpri" {
                            position 6;
                          }
                          ext:bit "pcri" {
                            position 7;
                          }
                          ext:bit "suppressed" {
                            position 8;
                          }
                          ext:bit "NHP-EMPTY" {
                            position 9;
                          }
                          ext:bit "NO-ADV" {
                            position 10;
                          }
                          ext:bit "local_cross" {
                            position 11;
                          }
                          ext:bit "remote_cross" {
                            position 12;
                          }
                          ext:bit "VD-BGP" {
                            position 13;
                          }
                          ext:bit "PATH_LOCAL" {
                            position 14;
                          }
                          ext:bit "PATH_GATEWAY" {
                            position 15;
                          }
                          ext:bit "policy_nopass" {
                            position 16;
                          }
                          ext:bit "supprenet" {
                            position 17;
                          }
                          ext:bit "dampened" {
                            position 18;
                          }
                          ext:bit "history" {
                            position 19;
                          }
                          ext:bit "select" {
                            position 20;
                          }
                          ext:bit "best" {
                            position 21;
                          }
                          ext:bit "backup" {
                            position 22;
                          }
                          ext:bit "attr_change" {
                            position 23;
                          }
                          ext:bit "NHLFE_CREATED" {
                            position 24;
                          }
                          ext:bit "ILM_CREATED" {
                            position 25;
                          }
                          ext:bit "NEXTHOP_CHANGE" {
                            position 26;
                          }
                          ext:bit "Invaild" {
                            position 27;
                          }
                          ext:bit "SOURCE_CHANGE" {
                            position 28;
                          }
                          ext:bit "IN_SELECTEDQ" {
                            position 29;
                          }
                          ext:bit "EXITIF_ERROR" {
                            position 30;
                          }
                          ext:bit "GROUP_HEAD" {
                            position 31;
                          }
                      }
                      config false;
                      description
                        "Route type.";
                    }
                    leaf ngAsIpString {
                      type string {
                        length "1..300";
                      }
                      config false;
                      description
                        "Ng Route prefix information.";
                    }
                    leaf ngPmsiString {
                      type string {
                        length "1..300";
                      }
                      config false;
                      description
                        "PMSI attribute.";
                    }
                    leaf advNextHop {
                      type inet:ip-address-no-zone;
                      config false;
                      description
                        "Next hop of an BGP.";
                    }
                  }
                }
                container peerNgAdvRtTable1s {
                  config false;
                  description
                    "List of displayed BGP Ng Adv route type 1 information.";
                  list peerNgAdvRtTable1 {
                    when "not(../../../../afType!='mvpn' and ../../../../afType!='mvpnv6')";
                    key "ngNlri rd from ngRouteType routeTypeFlag";
                    config false;
                    description
                      "Information about BGP Ng Adv routes type 1.";
                    leaf ngNlri {
                      type inet:ipv4-address-no-zone;
                      config false;
                      description
                        "Prefix of a BGP route.";
                    }
                    leaf imTableId {
                      type uint32 {
                        range "0..4294967295";
                      }
                      config false;
                      description
                        "ID of the routing table to which routes are imported.";
                    }
                    leaf nexthop {
                      type inet:ip-address-no-zone;
                      config false;
                      description
                        "Next hop address to which packets are forwarded.";
                    }
                    leaf locPrf {
                      type uint32 {
                        range "0..4294967295";
                      }
                      config false;
                      description
                        "Local-preference.";
                    }
                    leaf prefVal {
                      type uint32 {
                        range "0..4294967295";
                      }
                      config false;
                      description
                        "Preferred value of a protocol.";
                    }
                    leaf prefrence {
                      type uint8 {
                        range "0..255";
                      }
                      config false;
                      description
                        "Priority of BGP routes.";
                    }
                    leaf pathAs {
                      type string {
                        length "1..300";
                      }
                      config false;
                      description
                        "List of the AS_Paths that packets pass through.";
                    }
                    leaf origin {
                      type bgpcommOrigin;
                      config false;
                      description
                        "Route origin.";
                    }
                    leaf med {
                      type uint32 {
                        range "0..4294967295";
                      }
                      config false;
                      description
                        "Route MED.";
                    }
                    leaf flagString {
                      type string {
                        length "1..100";
                      }
                      config false;
                      description
                        "Route flag that contains a string of characters.";
                    }
                    leaf rd {
                      type string {
                        length "1..22";
                      }
                      config false;
                      description
                        "Route distinguisher.";
                    }
                    leaf rtWorseReason {
                      type string {
                        length "1..50";
                      }
                      config false;
                      description
                        "Reason why a route is not selected.";
                    }
                    leaf peerString {
                      type string {
                        length "1..300";
                      }
                      config false;
                      description
                        "List of route sending peers.";
                    }
                    leaf time {
                      type uint32 {
                        range "0..4294967295";
                      }
                      config false;
                      description
                        "Time stamp of a route.";
                    }
                    leaf community {
                      type string {
                        length "1..120";
                      }
                      config false;
                      description
                        "Community attribute.";
                    }
                    leaf extCommunity {
                      type string {
                        length "1..300";
                      }
                      config false;
                      description
                        "Extended community attribute.";
                    }
                    leaf from {
                      type inet:ip-address-no-zone;
                      config false;
                      description
                        "Source peer that sends a route.";
                    }
                    leaf ifName {
                      type pub-type:ifName;
                      config false;
                      description
                        "Name of the outbound interface of a route.";
                    }
                    leaf originator {
                      type inet:ip-address-no-zone;
                      config false;
                      description
                        "Router ID of the route initiator.";
                    }
                    leaf clusterList {
                      type string {
                        length "1..300";
                      }
                      config false;
                      description
                        "List of cluster IDs.";
                    }
                    leaf remoteRouteId {
                      type inet:ipv4-address-no-zone;
                      config false;
                      description
                        "Router ID of a peer.";
                    }
                    leaf relayNexthop {
                      type inet:ip-address-no-zone;
                      config false;
                      description
                        "Next hop to which a route is iterated.";
                    }
                    leaf relaytnlName {
                      type string {
                        length "1..64";
                      }
                      config false;
                      description
                        "Name of a tunnel to which a route is iterated.";
                    }
                    leaf inLabel {
                      type uint32 {
                        range "0..4294967295";
                      }
                      config false;
                      description
                        "In-label.";
                    }
                    leaf outLabel {
                      type uint32 {
                        range "0..4294967295";
                      }
                      config false;
                      description
                        "Out-label.";
                    }
                    leaf ngRouteType {
                      type string {
                        length "1..50";
                      }
                      config false;
                      description
                        "Route type.";
                    }
                    leaf routeTypeFlag {
                      type pub-type:bits32 {
                        ext:masklen 32;
                          ext:bit "ibgp" {
                            position 0;
                          }
                          ext:bit "ebgp" {
                            position 1;
                          }
                          ext:bit "network" {
                            position 2;
                          }
                          ext:bit "import" {
                            position 3;
                          }
                          ext:bit "auto-summary" {
                            position 4;
                          }
                          ext:bit "aggregate" {
                            position 5;
                          }
                          ext:bit "cpri" {
                            position 6;
                          }
                          ext:bit "pcri" {
                            position 7;
                          }
                          ext:bit "suppressed" {
                            position 8;
                          }
                          ext:bit "NHP-EMPTY" {
                            position 9;
                          }
                          ext:bit "NO-ADV" {
                            position 10;
                          }
                          ext:bit "local_cross" {
                            position 11;
                          }
                          ext:bit "remote_cross" {
                            position 12;
                          }
                          ext:bit "VD-BGP" {
                            position 13;
                          }
                          ext:bit "PATH_LOCAL" {
                            position 14;
                          }
                          ext:bit "PATH_GATEWAY" {
                            position 15;
                          }
                          ext:bit "policy_nopass" {
                            position 16;
                          }
                          ext:bit "supprenet" {
                            position 17;
                          }
                          ext:bit "dampened" {
                            position 18;
                          }
                          ext:bit "history" {
                            position 19;
                          }
                          ext:bit "select" {
                            position 20;
                          }
                          ext:bit "best" {
                            position 21;
                          }
                          ext:bit "backup" {
                            position 22;
                          }
                          ext:bit "attr_change" {
                            position 23;
                          }
                          ext:bit "NHLFE_CREATED" {
                            position 24;
                          }
                          ext:bit "ILM_CREATED" {
                            position 25;
                          }
                          ext:bit "NEXTHOP_CHANGE" {
                            position 26;
                          }
                          ext:bit "Invaild" {
                            position 27;
                          }
                          ext:bit "SOURCE_CHANGE" {
                            position 28;
                          }
                          ext:bit "IN_SELECTEDQ" {
                            position 29;
                          }
                          ext:bit "EXITIF_ERROR" {
                            position 30;
                          }
                          ext:bit "GROUP_HEAD" {
                            position 31;
                          }
                      }
                      config false;
                      description
                        "Route type.";
                    }
                    leaf ngAsIpString {
                      type string {
                        length "1..300";
                      }
                      config false;
                      description
                        "Ng Route prefix information.";
                    }
                    leaf ngPmsiString {
                      type string {
                        length "1..300";
                      }
                      config false;
                      description
                        "PMSI attribute.";
                    }
                    leaf advNextHop {
                      type inet:ip-address-no-zone;
                      config false;
                      description
                        "Next hop of an BGP.";
                    }
                  }
                }
                container peerNgRevRtTable2s {
                  config false;
                  description
                    "List of displayed BGP Ng Rev route type 2 information.";
                  list peerNgRevRtTable2 {
                    when "not(../../../../afType!='mvpn' and ../../../../afType!='mvpnv6')";
                    key "ngNlri rd from ngRouteType routeTypeFlag";
                    config false;
                    description
                      "Information about BGP Ng Rev routes type 2.";
                    leaf ngNlri {
                      type inet:ipv4-address-no-zone;
                      config false;
                      description
                        "Prefix of a BGP route.";
                    }
                    leaf imTableId {
                      type uint32 {
                        range "0..4294967295";
                      }
                      config false;
                      description
                        "ID of the routing table to which routes are imported.";
                    }
                    leaf nexthop {
                      type inet:ip-address-no-zone;
                      config false;
                      description
                        "Next hop address to which packets are forwarded.";
                    }
                    leaf locPrf {
                      type uint32 {
                        range "0..4294967295";
                      }
                      config false;
                      description
                        "Local-preference.";
                    }
                    leaf prefVal {
                      type uint32 {
                        range "0..4294967295";
                      }
                      config false;
                      description
                        "Preferred value of a protocol.";
                    }
                    leaf prefrence {
                      type uint8 {
                        range "0..255";
                      }
                      config false;
                      description
                        "Priority of BGP routes.";
                    }
                    leaf pathAs {
                      type string {
                        length "1..300";
                      }
                      config false;
                      description
                        "List of the AS_Paths that packets pass through.";
                    }
                    leaf origin {
                      type bgpcommOrigin;
                      config false;
                      description
                        "Route origin.";
                    }
                    leaf med {
                      type uint32 {
                        range "0..4294967295";
                      }
                      config false;
                      description
                        "Route MED.";
                    }
                    leaf flagString {
                      type string {
                        length "1..100";
                      }
                      config false;
                      description
                        "Route flag that contains a string of characters.";
                    }
                    leaf rd {
                      type string {
                        length "1..22";
                      }
                      config false;
                      description
                        "Route distinguisher.";
                    }
                    leaf rtWorseReason {
                      type string {
                        length "1..50";
                      }
                      config false;
                      description
                        "Reason why a route is not selected.";
                    }
                    leaf peerString {
                      type string {
                        length "1..300";
                      }
                      config false;
                      description
                        "List of route sending peers.";
                    }
                    leaf time {
                      type uint32 {
                        range "0..4294967295";
                      }
                      config false;
                      description
                        "Time stamp of a route.";
                    }
                    leaf community {
                      type string {
                        length "1..120";
                      }
                      config false;
                      description
                        "Community attribute.";
                    }
                    leaf extCommunity {
                      type string {
                        length "1..300";
                      }
                      config false;
                      description
                        "Extended community attribute.";
                    }
                    leaf from {
                      type inet:ip-address-no-zone;
                      config false;
                      description
                        "Source peer that sends a route.";
                    }
                    leaf ifName {
                      type pub-type:ifName;
                      config false;
                      description
                        "Name of the outbound interface of a route.";
                    }
                    leaf originator {
                      type inet:ip-address-no-zone;
                      config false;
                      description
                        "Router ID of the route initiator.";
                    }
                    leaf clusterList {
                      type string {
                        length "1..300";
                      }
                      config false;
                      description
                        "List of cluster IDs.";
                    }
                    leaf remoteRouteId {
                      type inet:ipv4-address-no-zone;
                      config false;
                      description
                        "Router ID of a peer.";
                    }
                    leaf relayNexthop {
                      type inet:ip-address-no-zone;
                      config false;
                      description
                        "Next hop to which a route is iterated.";
                    }
                    leaf relaytnlName {
                      type string {
                        length "1..64";
                      }
                      config false;
                      description
                        "Name of a tunnel to which a route is iterated.";
                    }
                    leaf inLabel {
                      type uint32 {
                        range "0..4294967295";
                      }
                      config false;
                      description
                        "In-label.";
                    }
                    leaf outLabel {
                      type uint32 {
                        range "0..4294967295";
                      }
                      config false;
                      description
                        "Out-label.";
                    }
                    leaf ngRouteType {
                      type string {
                        length "1..50";
                      }
                      config false;
                      description
                        "Route type.";
                    }
                    leaf routeTypeFlag {
                      type pub-type:bits32 {
                        ext:masklen 32;
                          ext:bit "ibgp" {
                            position 0;
                          }
                          ext:bit "ebgp" {
                            position 1;
                          }
                          ext:bit "network" {
                            position 2;
                          }
                          ext:bit "import" {
                            position 3;
                          }
                          ext:bit "auto-summary" {
                            position 4;
                          }
                          ext:bit "aggregate" {
                            position 5;
                          }
                          ext:bit "cpri" {
                            position 6;
                          }
                          ext:bit "pcri" {
                            position 7;
                          }
                          ext:bit "suppressed" {
                            position 8;
                          }
                          ext:bit "NHP-EMPTY" {
                            position 9;
                          }
                          ext:bit "NO-ADV" {
                            position 10;
                          }
                          ext:bit "local_cross" {
                            position 11;
                          }
                          ext:bit "remote_cross" {
                            position 12;
                          }
                          ext:bit "VD-BGP" {
                            position 13;
                          }
                          ext:bit "PATH_LOCAL" {
                            position 14;
                          }
                          ext:bit "PATH_GATEWAY" {
                            position 15;
                          }
                          ext:bit "policy_nopass" {
                            position 16;
                          }
                          ext:bit "supprenet" {
                            position 17;
                          }
                          ext:bit "dampened" {
                            position 18;
                          }
                          ext:bit "history" {
                            position 19;
                          }
                          ext:bit "select" {
                            position 20;
                          }
                          ext:bit "best" {
                            position 21;
                          }
                          ext:bit "backup" {
                            position 22;
                          }
                          ext:bit "attr_change" {
                            position 23;
                          }
                          ext:bit "NHLFE_CREATED" {
                            position 24;
                          }
                          ext:bit "ILM_CREATED" {
                            position 25;
                          }
                          ext:bit "NEXTHOP_CHANGE" {
                            position 26;
                          }
                          ext:bit "Invaild" {
                            position 27;
                          }
                          ext:bit "SOURCE_CHANGE" {
                            position 28;
                          }
                          ext:bit "IN_SELECTEDQ" {
                            position 29;
                          }
                          ext:bit "EXITIF_ERROR" {
                            position 30;
                          }
                          ext:bit "GROUP_HEAD" {
                            position 31;
                          }
                      }
                      config false;
                      description
                        "Route type.";
                    }
                    leaf ngAsIpString {
                      type string {
                        length "1..300";
                      }
                      config false;
                      description
                        "Ng Route Prefix Information.";
                    }
                    leaf advNextHop {
                      type inet:ip-address-no-zone;
                      config false;
                      description
                        "Next hop of an BGP.";
                    }
                  }
                }
                container peerNgAdvRtTable2s {
                  config false;
                  description
                    "List of displayed BGP Ng Adv route type 2 information.";
                  list peerNgAdvRtTable2 {
                    when "not(../../../../afType!='mvpn' and ../../../../afType!='mvpnv6')";
                    key "ngNlri rd from ngRouteType routeTypeFlag";
                    config false;
                    description
                      "Information about BGP Ng Adv routes type 2.";
                    leaf ngNlri {
                      type inet:ipv4-address-no-zone;
                      config false;
                      description
                        "Prefix of a BGP route.";
                    }
                    leaf imTableId {
                      type uint32 {
                        range "0..4294967295";
                      }
                      config false;
                      description
                        "ID of the routing table to which routes are imported.";
                    }
                    leaf nexthop {
                      type inet:ip-address-no-zone;
                      config false;
                      description
                        "Next hop address to which packets are forwarded.";
                    }
                    leaf locPrf {
                      type uint32 {
                        range "0..4294967295";
                      }
                      config false;
                      description
                        "Local-preference.";
                    }
                    leaf prefVal {
                      type uint32 {
                        range "0..4294967295";
                      }
                      config false;
                      description
                        "Preferred value of a protocol.";
                    }
                    leaf prefrence {
                      type uint8 {
                        range "0..255";
                      }
                      config false;
                      description
                        "Priority of BGP routes.";
                    }
                    leaf pathAs {
                      type string {
                        length "1..300";
                      }
                      config false;
                      description
                        "List of the AS_Paths that packets pass through.";
                    }
                    leaf origin {
                      type bgpcommOrigin;
                      config false;
                      description
                        "Route origin.";
                    }
                    leaf med {
                      type uint32 {
                        range "0..4294967295";
                      }
                      config false;
                      description
                        "Route MED.";
                    }
                    leaf flagString {
                      type string {
                        length "1..100";
                      }
                      config false;
                      description
                        "Route flag that contains a string of characters.";
                    }
                    leaf rd {
                      type string {
                        length "1..22";
                      }
                      config false;
                      description
                        "Route distinguisher.";
                    }
                    leaf rtWorseReason {
                      type string {
                        length "1..50";
                      }
                      config false;
                      description
                        "Reason why a route is not selected.";
                    }
                    leaf peerString {
                      type string {
                        length "1..300";
                      }
                      config false;
                      description
                        "List of route sending peers.";
                    }
                    leaf time {
                      type uint32 {
                        range "0..4294967295";
                      }
                      config false;
                      description
                        "Time stamp of a route.";
                    }
                    leaf community {
                      type string {
                        length "1..120";
                      }
                      config false;
                      description
                        "Community attribute.";
                    }
                    leaf extCommunity {
                      type string {
                        length "1..300";
                      }
                      config false;
                      description
                        "Extended community attribute.";
                    }
                    leaf from {
                      type inet:ip-address-no-zone;
                      config false;
                      description
                        "Source peer that sends a route.";
                    }
                    leaf ifName {
                      type pub-type:ifName;
                      config false;
                      description
                        "Name of the outbound interface of a route.";
                    }
                    leaf originator {
                      type inet:ip-address-no-zone;
                      config false;
                      description
                        "Router ID of the route initiator.";
                    }
                    leaf clusterList {
                      type string {
                        length "1..300";
                      }
                      config false;
                      description
                        "List of cluster IDs.";
                    }
                    leaf remoteRouteId {
                      type inet:ipv4-address-no-zone;
                      config false;
                      description
                        "Router ID of a peer.";
                    }
                    leaf relayNexthop {
                      type inet:ip-address-no-zone;
                      config false;
                      description
                        "Next hop to which a route is iterated.";
                    }
                    leaf relaytnlName {
                      type string {
                        length "1..64";
                      }
                      config false;
                      description
                        "Name of a tunnel to which a route is iterated.";
                    }
                    leaf inLabel {
                      type uint32 {
                        range "0..4294967295";
                      }
                      config false;
                      description
                        "In-label.";
                    }
                    leaf outLabel {
                      type uint32 {
                        range "0..4294967295";
                      }
                      config false;
                      description
                        "Out-label.";
                    }
                    leaf ngRouteType {
                      type string {
                        length "1..50";
                      }
                      config false;
                      description
                        "Route type.";
                    }
                    leaf routeTypeFlag {
                      type pub-type:bits32 {
                        ext:masklen 32;
                          ext:bit "ibgp" {
                            position 0;
                          }
                          ext:bit "ebgp" {
                            position 1;
                          }
                          ext:bit "network" {
                            position 2;
                          }
                          ext:bit "import" {
                            position 3;
                          }
                          ext:bit "auto-summary" {
                            position 4;
                          }
                          ext:bit "aggregate" {
                            position 5;
                          }
                          ext:bit "cpri" {
                            position 6;
                          }
                          ext:bit "pcri" {
                            position 7;
                          }
                          ext:bit "suppressed" {
                            position 8;
                          }
                          ext:bit "NHP-EMPTY" {
                            position 9;
                          }
                          ext:bit "NO-ADV" {
                            position 10;
                          }
                          ext:bit "local_cross" {
                            position 11;
                          }
                          ext:bit "remote_cross" {
                            position 12;
                          }
                          ext:bit "VD-BGP" {
                            position 13;
                          }
                          ext:bit "PATH_LOCAL" {
                            position 14;
                          }
                          ext:bit "PATH_GATEWAY" {
                            position 15;
                          }
                          ext:bit "policy_nopass" {
                            position 16;
                          }
                          ext:bit "supprenet" {
                            position 17;
                          }
                          ext:bit "dampened" {
                            position 18;
                          }
                          ext:bit "history" {
                            position 19;
                          }
                          ext:bit "select" {
                            position 20;
                          }
                          ext:bit "best" {
                            position 21;
                          }
                          ext:bit "backup" {
                            position 22;
                          }
                          ext:bit "attr_change" {
                            position 23;
                          }
                          ext:bit "NHLFE_CREATED" {
                            position 24;
                          }
                          ext:bit "ILM_CREATED" {
                            position 25;
                          }
                          ext:bit "NEXTHOP_CHANGE" {
                            position 26;
                          }
                          ext:bit "Invaild" {
                            position 27;
                          }
                          ext:bit "SOURCE_CHANGE" {
                            position 28;
                          }
                          ext:bit "IN_SELECTEDQ" {
                            position 29;
                          }
                          ext:bit "EXITIF_ERROR" {
                            position 30;
                          }
                          ext:bit "GROUP_HEAD" {
                            position 31;
                          }
                      }
                      config false;
                      description
                        "Route type.";
                    }
                    leaf ngAsIpString {
                      type string {
                        length "1..300";
                      }
                      config false;
                      description
                        "Ng Route Prefix Information.";
                    }
                    leaf advNextHop {
                      type inet:ip-address-no-zone;
                      config false;
                      description
                        "Next hop of an BGP.";
                    }
                  }
                }
                container peerNgRevRtTable3s {
                  config false;
                  description
                    "List of displayed BGP Ng Rev route type 3 information.";
                  list peerNgRevRtTable3 {
                    when "not(../../../../afType!='mvpn' and ../../../../afType!='mvpnv6')";
                    key "ngNlri rd from ngRouteType routeTypeFlag";
                    config false;
                    description
                      "Information about BGP Ng Rev routes type 3.";
                    leaf ngNlri {
                      type inet:ipv4-address-no-zone;
                      config false;
                      description
                        "Prefix of a BGP route.";
                    }
                    leaf imTableId {
                      type uint32 {
                        range "0..4294967295";
                      }
                      config false;
                      description
                        "ID of the routing table to which routes are imported.";
                    }
                    leaf nexthop {
                      type inet:ip-address-no-zone;
                      config false;
                      description
                        "Next hop address to which packets are forwarded.";
                    }
                    leaf locPrf {
                      type uint32 {
                        range "0..4294967295";
                      }
                      config false;
                      description
                        "Local-preference.";
                    }
                    leaf prefVal {
                      type uint32 {
                        range "0..4294967295";
                      }
                      config false;
                      description
                        "Preferred value of a protocol.";
                    }
                    leaf prefrence {
                      type uint8 {
                        range "0..255";
                      }
                      config false;
                      description
                        "Priority of BGP routes.";
                    }
                    leaf pathAs {
                      type string {
                        length "1..300";
                      }
                      config false;
                      description
                        "List of the AS_Paths that packets pass through.";
                    }
                    leaf origin {
                      type bgpcommOrigin;
                      config false;
                      description
                        "Route origin.";
                    }
                    leaf med {
                      type uint32 {
                        range "0..4294967295";
                      }
                      config false;
                      description
                        "Route MED.";
                    }
                    leaf flagString {
                      type string {
                        length "1..100";
                      }
                      config false;
                      description
                        "Route flag that contains a string of characters.";
                    }
                    leaf rd {
                      type string {
                        length "1..22";
                      }
                      config false;
                      description
                        "Route distinguisher.";
                    }
                    leaf rtWorseReason {
                      type string {
                        length "1..50";
                      }
                      config false;
                      description
                        "Reason why a route is not selected.";
                    }
                    leaf peerString {
                      type string {
                        length "1..300";
                      }
                      config false;
                      description
                        "List of route sending peers.";
                    }
                    leaf time {
                      type uint32 {
                        range "0..4294967295";
                      }
                      config false;
                      description
                        "Time stamp of a route.";
                    }
                    leaf community {
                      type string {
                        length "1..120";
                      }
                      config false;
                      description
                        "Community attribute.";
                    }
                    leaf extCommunity {
                      type string {
                        length "1..300";
                      }
                      config false;
                      description
                        "Extended community attribute.";
                    }
                    leaf from {
                      type inet:ip-address-no-zone;
                      config false;
                      description
                        "Source peer that sends a route.";
                    }
                    leaf ifName {
                      type pub-type:ifName;
                      config false;
                      description
                        "Name of the outbound interface of a route.";
                    }
                    leaf originator {
                      type inet:ip-address-no-zone;
                      config false;
                      description
                        "Router ID of the route initiator.";
                    }
                    leaf clusterList {
                      type string {
                        length "1..300";
                      }
                      config false;
                      description
                        "List of cluster IDs.";
                    }
                    leaf remoteRouteId {
                      type inet:ipv4-address-no-zone;
                      config false;
                      description
                        "Router ID of a peer.";
                    }
                    leaf relayNexthop {
                      type inet:ip-address-no-zone;
                      config false;
                      description
                        "Next hop to which a route is iterated.";
                    }
                    leaf relaytnlName {
                      type string {
                        length "1..64";
                      }
                      config false;
                      description
                        "Name of a tunnel to which a route is iterated.";
                    }
                    leaf inLabel {
                      type uint32 {
                        range "0..4294967295";
                      }
                      config false;
                      description
                        "In-label.";
                    }
                    leaf outLabel {
                      type uint32 {
                        range "0..4294967295";
                      }
                      config false;
                      description
                        "Out-label.";
                    }
                    leaf ngRouteType {
                      type string {
                        length "1..50";
                      }
                      config false;
                      description
                        "Route type.";
                    }
                    leaf routeTypeFlag {
                      type pub-type:bits32 {
                        ext:masklen 32;
                          ext:bit "ibgp" {
                            position 0;
                          }
                          ext:bit "ebgp" {
                            position 1;
                          }
                          ext:bit "network" {
                            position 2;
                          }
                          ext:bit "import" {
                            position 3;
                          }
                          ext:bit "auto-summary" {
                            position 4;
                          }
                          ext:bit "aggregate" {
                            position 5;
                          }
                          ext:bit "cpri" {
                            position 6;
                          }
                          ext:bit "pcri" {
                            position 7;
                          }
                          ext:bit "suppressed" {
                            position 8;
                          }
                          ext:bit "NHP-EMPTY" {
                            position 9;
                          }
                          ext:bit "NO-ADV" {
                            position 10;
                          }
                          ext:bit "local_cross" {
                            position 11;
                          }
                          ext:bit "remote_cross" {
                            position 12;
                          }
                          ext:bit "VD-BGP" {
                            position 13;
                          }
                          ext:bit "PATH_LOCAL" {
                            position 14;
                          }
                          ext:bit "PATH_GATEWAY" {
                            position 15;
                          }
                          ext:bit "policy_nopass" {
                            position 16;
                          }
                          ext:bit "supprenet" {
                            position 17;
                          }
                          ext:bit "dampened" {
                            position 18;
                          }
                          ext:bit "history" {
                            position 19;
                          }
                          ext:bit "select" {
                            position 20;
                          }
                          ext:bit "best" {
                            position 21;
                          }
                          ext:bit "backup" {
                            position 22;
                          }
                          ext:bit "attr_change" {
                            position 23;
                          }
                          ext:bit "NHLFE_CREATED" {
                            position 24;
                          }
                          ext:bit "ILM_CREATED" {
                            position 25;
                          }
                          ext:bit "NEXTHOP_CHANGE" {
                            position 26;
                          }
                          ext:bit "Invaild" {
                            position 27;
                          }
                          ext:bit "SOURCE_CHANGE" {
                            position 28;
                          }
                          ext:bit "IN_SELECTEDQ" {
                            position 29;
                          }
                          ext:bit "EXITIF_ERROR" {
                            position 30;
                          }
                          ext:bit "GROUP_HEAD" {
                            position 31;
                          }
                      }
                      config false;
                      description
                        "Route type.";
                    }
                    leaf ngAsIpString {
                      type string {
                        length "1..300";
                      }
                      config false;
                      description
                        "Ng route prefix information.";
                    }
                    leaf advNextHop {
                      type inet:ip-address-no-zone;
                      config false;
                      description
                        "Next hop of an BGP.";
                    }
                  }
                }
                container peerNgAdvRtTable3s {
                  config false;
                  description
                    "List of displayed BGP Ng Adv route type 3 information.";
                  list peerNgAdvRtTable3 {
                    when "not(../../../../afType!='mvpn' and ../../../../afType!='mvpnv6')";
                    key "ngNlri rd from ngRouteType routeTypeFlag";
                    config false;
                    description
                      "Information about BGP Ng Adv routes type 3.";
                    leaf ngNlri {
                      type inet:ipv4-address-no-zone;
                      config false;
                      description
                        "Prefix of a BGP route.";
                    }
                    leaf imTableId {
                      type uint32 {
                        range "0..4294967295";
                      }
                      config false;
                      description
                        "ID of the routing table to which routes are imported.";
                    }
                    leaf nexthop {
                      type inet:ip-address-no-zone;
                      config false;
                      description
                        "Next hop address to which packets are forwarded.";
                    }
                    leaf locPrf {
                      type uint32 {
                        range "0..4294967295";
                      }
                      config false;
                      description
                        "Local-preference.";
                    }
                    leaf prefVal {
                      type uint32 {
                        range "0..4294967295";
                      }
                      config false;
                      description
                        "Preferred value of a protocol.";
                    }
                    leaf prefrence {
                      type uint8 {
                        range "0..255";
                      }
                      config false;
                      description
                        "Priority of BGP routes.";
                    }
                    leaf pathAs {
                      type string {
                        length "1..300";
                      }
                      config false;
                      description
                        "List of the AS_Paths that packets pass through.";
                    }
                    leaf origin {
                      type bgpcommOrigin;
                      config false;
                      description
                        "Route origin.";
                    }
                    leaf med {
                      type uint32 {
                        range "0..4294967295";
                      }
                      config false;
                      description
                        "Route MED.";
                    }
                    leaf flagString {
                      type string {
                        length "1..100";
                      }
                      config false;
                      description
                        "Route flag that contains a string of characters.";
                    }
                    leaf rd {
                      type string {
                        length "1..22";
                      }
                      config false;
                      description
                        "Route distinguisher.";
                    }
                    leaf rtWorseReason {
                      type string {
                        length "1..50";
                      }
                      config false;
                      description
                        "Reason why a route is not selected.";
                    }
                    leaf peerString {
                      type string {
                        length "1..300";
                      }
                      config false;
                      description
                        "List of route sending peers.";
                    }
                    leaf time {
                      type uint32 {
                        range "0..4294967295";
                      }
                      config false;
                      description
                        "Time stamp of a route.";
                    }
                    leaf community {
                      type string {
                        length "1..120";
                      }
                      config false;
                      description
                        "Community attribute.";
                    }
                    leaf extCommunity {
                      type string {
                        length "1..300";
                      }
                      config false;
                      description
                        "Extended community attribute.";
                    }
                    leaf from {
                      type inet:ip-address-no-zone;
                      config false;
                      description
                        "Source peer that sends a route.";
                    }
                    leaf ifName {
                      type pub-type:ifName;
                      config false;
                      description
                        "Name of the outbound interface of a route.";
                    }
                    leaf originator {
                      type inet:ip-address-no-zone;
                      config false;
                      description
                        "Router ID of the route initiator.";
                    }
                    leaf clusterList {
                      type string {
                        length "1..300";
                      }
                      config false;
                      description
                        "List of cluster IDs.";
                    }
                    leaf remoteRouteId {
                      type inet:ipv4-address-no-zone;
                      config false;
                      description
                        "Router ID of a peer.";
                    }
                    leaf relayNexthop {
                      type inet:ip-address-no-zone;
                      config false;
                      description
                        "Next hop to which a route is iterated.";
                    }
                    leaf relaytnlName {
                      type string {
                        length "1..64";
                      }
                      config false;
                      description
                        "Name of a tunnel to which a route is iterated.";
                    }
                    leaf inLabel {
                      type uint32 {
                        range "0..4294967295";
                      }
                      config false;
                      description
                        "In-label.";
                    }
                    leaf outLabel {
                      type uint32 {
                        range "0..4294967295";
                      }
                      config false;
                      description
                        "Out-label.";
                    }
                    leaf ngRouteType {
                      type string {
                        length "1..50";
                      }
                      config false;
                      description
                        "Route type.";
                    }
                    leaf routeTypeFlag {
                      type pub-type:bits32 {
                        ext:masklen 32;
                          ext:bit "ibgp" {
                            position 0;
                          }
                          ext:bit "ebgp" {
                            position 1;
                          }
                          ext:bit "network" {
                            position 2;
                          }
                          ext:bit "import" {
                            position 3;
                          }
                          ext:bit "auto-summary" {
                            position 4;
                          }
                          ext:bit "aggregate" {
                            position 5;
                          }
                          ext:bit "cpri" {
                            position 6;
                          }
                          ext:bit "pcri" {
                            position 7;
                          }
                          ext:bit "suppressed" {
                            position 8;
                          }
                          ext:bit "NHP-EMPTY" {
                            position 9;
                          }
                          ext:bit "NO-ADV" {
                            position 10;
                          }
                          ext:bit "local_cross" {
                            position 11;
                          }
                          ext:bit "remote_cross" {
                            position 12;
                          }
                          ext:bit "VD-BGP" {
                            position 13;
                          }
                          ext:bit "PATH_LOCAL" {
                            position 14;
                          }
                          ext:bit "PATH_GATEWAY" {
                            position 15;
                          }
                          ext:bit "policy_nopass" {
                            position 16;
                          }
                          ext:bit "supprenet" {
                            position 17;
                          }
                          ext:bit "dampened" {
                            position 18;
                          }
                          ext:bit "history" {
                            position 19;
                          }
                          ext:bit "select" {
                            position 20;
                          }
                          ext:bit "best" {
                            position 21;
                          }
                          ext:bit "backup" {
                            position 22;
                          }
                          ext:bit "attr_change" {
                            position 23;
                          }
                          ext:bit "NHLFE_CREATED" {
                            position 24;
                          }
                          ext:bit "ILM_CREATED" {
                            position 25;
                          }
                          ext:bit "NEXTHOP_CHANGE" {
                            position 26;
                          }
                          ext:bit "Invaild" {
                            position 27;
                          }
                          ext:bit "SOURCE_CHANGE" {
                            position 28;
                          }
                          ext:bit "IN_SELECTEDQ" {
                            position 29;
                          }
                          ext:bit "EXITIF_ERROR" {
                            position 30;
                          }
                          ext:bit "GROUP_HEAD" {
                            position 31;
                          }
                      }
                      config false;
                      description
                        "Route type.";
                    }
                    leaf ngAsIpString {
                      type string {
                        length "1..300";
                      }
                      config false;
                      description
                        "Ng route prefix information.";
                    }
                    leaf advNextHop {
                      type inet:ip-address-no-zone;
                      config false;
                      description
                        "Next hop of an BGP.";
                    }
                  }
                }
                container peerNgRevRtTable4s {
                  config false;
                  description
                    "List of displayed BGP Ng Rev route type 4 information.";
                  list peerNgRevRtTable4 {
                    when "not(../../../../afType!='mvpn' and ../../../../afType!='mvpnv6')";
                    key "ngNlri rd from ngRouteType routeTypeFlag";
                    config false;
                    description
                      "Information about BGP Ng Rev routes type 4.";
                    leaf ngNlri {
                      type inet:ipv4-address-no-zone;
                      config false;
                      description
                        "Prefix of a BGP route.";
                    }
                    leaf imTableId {
                      type uint32 {
                        range "0..4294967295";
                      }
                      config false;
                      description
                        "ID of the routing table to which routes are imported.";
                    }
                    leaf nexthop {
                      type inet:ip-address-no-zone;
                      config false;
                      description
                        "Next hop address to which packets are forwarded.";
                    }
                    leaf locPrf {
                      type uint32 {
                        range "0..4294967295";
                      }
                      config false;
                      description
                        "Local-preference.";
                    }
                    leaf prefVal {
                      type uint32 {
                        range "0..4294967295";
                      }
                      config false;
                      description
                        "Preferred value of a protocol.";
                    }
                    leaf prefrence {
                      type uint8 {
                        range "0..255";
                      }
                      config false;
                      description
                        "Priority of BGP routes.";
                    }
                    leaf pathAs {
                      type string {
                        length "1..300";
                      }
                      config false;
                      description
                        "List of the AS_Paths that packets pass through.";
                    }
                    leaf origin {
                      type bgpcommOrigin;
                      config false;
                      description
                        "Route origin.";
                    }
                    leaf med {
                      type uint32 {
                        range "0..4294967295";
                      }
                      config false;
                      description
                        "Route MED.";
                    }
                    leaf flagString {
                      type string {
                        length "1..100";
                      }
                      config false;
                      description
                        "Route flag that contains a string of characters.";
                    }
                    leaf rd {
                      type string {
                        length "1..22";
                      }
                      config false;
                      description
                        "Route distinguisher.";
                    }
                    leaf rtWorseReason {
                      type string {
                        length "1..50";
                      }
                      config false;
                      description
                        "Reason why a route is not selected.";
                    }
                    leaf peerString {
                      type string {
                        length "1..300";
                      }
                      config false;
                      description
                        "List of route sending peers.";
                    }
                    leaf time {
                      type uint32 {
                        range "0..4294967295";
                      }
                      config false;
                      description
                        "Time stamp of a route.";
                    }
                    leaf community {
                      type string {
                        length "1..120";
                      }
                      config false;
                      description
                        "Community attribute.";
                    }
                    leaf extCommunity {
                      type string {
                        length "1..300";
                      }
                      config false;
                      description
                        "Extended community attribute.";
                    }
                    leaf from {
                      type inet:ip-address-no-zone;
                      config false;
                      description
                        "Source peer that sends a route.";
                    }
                    leaf ifName {
                      type pub-type:ifName;
                      config false;
                      description
                        "Name of the outbound interface of a route.";
                    }
                    leaf originator {
                      type inet:ip-address-no-zone;
                      config false;
                      description
                        "Router ID of the route initiator.";
                    }
                    leaf clusterList {
                      type string {
                        length "1..300";
                      }
                      config false;
                      description
                        "List of cluster IDs.";
                    }
                    leaf remoteRouteId {
                      type inet:ipv4-address-no-zone;
                      config false;
                      description
                        "Router ID of a peer.";
                    }
                    leaf relayNexthop {
                      type inet:ip-address-no-zone;
                      config false;
                      description
                        "Next hop to which a route is iterated.";
                    }
                    leaf relaytnlName {
                      type string {
                        length "1..64";
                      }
                      config false;
                      description
                        "Name of a tunnel to which a route is iterated.";
                    }
                    leaf inLabel {
                      type uint32 {
                        range "0..4294967295";
                      }
                      config false;
                      description
                        "In-label.";
                    }
                    leaf outLabel {
                      type uint32 {
                        range "0..4294967295";
                      }
                      config false;
                      description
                        "Out-label.";
                    }
                    leaf ngRouteType {
                      type string {
                        length "1..50";
                      }
                      config false;
                      description
                        "Route type.";
                    }
                    leaf routeTypeFlag {
                      type pub-type:bits32 {
                        ext:masklen 32;
                          ext:bit "ibgp" {
                            position 0;
                          }
                          ext:bit "ebgp" {
                            position 1;
                          }
                          ext:bit "network" {
                            position 2;
                          }
                          ext:bit "import" {
                            position 3;
                          }
                          ext:bit "auto-summary" {
                            position 4;
                          }
                          ext:bit "aggregate" {
                            position 5;
                          }
                          ext:bit "cpri" {
                            position 6;
                          }
                          ext:bit "pcri" {
                            position 7;
                          }
                          ext:bit "suppressed" {
                            position 8;
                          }
                          ext:bit "NHP-EMPTY" {
                            position 9;
                          }
                          ext:bit "NO-ADV" {
                            position 10;
                          }
                          ext:bit "local_cross" {
                            position 11;
                          }
                          ext:bit "remote_cross" {
                            position 12;
                          }
                          ext:bit "VD-BGP" {
                            position 13;
                          }
                          ext:bit "PATH_LOCAL" {
                            position 14;
                          }
                          ext:bit "PATH_GATEWAY" {
                            position 15;
                          }
                          ext:bit "policy_nopass" {
                            position 16;
                          }
                          ext:bit "supprenet" {
                            position 17;
                          }
                          ext:bit "dampened" {
                            position 18;
                          }
                          ext:bit "history" {
                            position 19;
                          }
                          ext:bit "select" {
                            position 20;
                          }
                          ext:bit "best" {
                            position 21;
                          }
                          ext:bit "backup" {
                            position 22;
                          }
                          ext:bit "attr_change" {
                            position 23;
                          }
                          ext:bit "NHLFE_CREATED" {
                            position 24;
                          }
                          ext:bit "ILM_CREATED" {
                            position 25;
                          }
                          ext:bit "NEXTHOP_CHANGE" {
                            position 26;
                          }
                          ext:bit "Invaild" {
                            position 27;
                          }
                          ext:bit "SOURCE_CHANGE" {
                            position 28;
                          }
                          ext:bit "IN_SELECTEDQ" {
                            position 29;
                          }
                          ext:bit "EXITIF_ERROR" {
                            position 30;
                          }
                          ext:bit "GROUP_HEAD" {
                            position 31;
                          }
                      }
                      config false;
                      description
                        "Route type.";
                    }
                    leaf ngAsIpString {
                      type string {
                        length "1..300";
                      }
                      config false;
                      description
                        "Ng route prefix information.";
                    }
                    leaf advNextHop {
                      type inet:ip-address-no-zone;
                      config false;
                      description
                        "Next hop of an BGP.";
                    }
                  }
                }
                container peerNgAdvRtTable4s {
                  config false;
                  description
                    "List of displayed BGP Ng Adv route type 4 information.";
                  list peerNgAdvRtTable4 {
                    when "not(../../../../afType!='mvpn' and ../../../../afType!='mvpnv6')";
                    key "ngNlri rd from ngRouteType routeTypeFlag";
                    config false;
                    description
                      "Information about BGP Ng Adv routes type 4.";
                    leaf ngNlri {
                      type inet:ipv4-address-no-zone;
                      config false;
                      description
                        "Prefix of a BGP route.";
                    }
                    leaf imTableId {
                      type uint32 {
                        range "0..4294967295";
                      }
                      config false;
                      description
                        "ID of the routing table to which routes are imported.";
                    }
                    leaf nexthop {
                      type inet:ip-address-no-zone;
                      config false;
                      description
                        "Next hop address to which packets are forwarded.";
                    }
                    leaf locPrf {
                      type uint32 {
                        range "0..4294967295";
                      }
                      config false;
                      description
                        "Local-preference.";
                    }
                    leaf prefVal {
                      type uint32 {
                        range "0..4294967295";
                      }
                      config false;
                      description
                        "Preferred value of a protocol.";
                    }
                    leaf prefrence {
                      type uint8 {
                        range "0..255";
                      }
                      config false;
                      description
                        "Priority of BGP routes.";
                    }
                    leaf pathAs {
                      type string {
                        length "1..300";
                      }
                      config false;
                      description
                        "List of the AS_Paths that packets pass through.";
                    }
                    leaf origin {
                      type bgpcommOrigin;
                      config false;
                      description
                        "Route origin.";
                    }
                    leaf med {
                      type uint32 {
                        range "0..4294967295";
                      }
                      config false;
                      description
                        "Route MED.";
                    }
                    leaf flagString {
                      type string {
                        length "1..100";
                      }
                      config false;
                      description
                        "Route flag that contains a string of characters.";
                    }
                    leaf rd {
                      type string {
                        length "1..22";
                      }
                      config false;
                      description
                        "Route distinguisher.";
                    }
                    leaf rtWorseReason {
                      type string {
                        length "1..50";
                      }
                      config false;
                      description
                        "Reason why a route is not selected.";
                    }
                    leaf peerString {
                      type string {
                        length "1..300";
                      }
                      config false;
                      description
                        "List of route sending peers.";
                    }
                    leaf time {
                      type uint32 {
                        range "0..4294967295";
                      }
                      config false;
                      description
                        "Time stamp of a route.";
                    }
                    leaf community {
                      type string {
                        length "1..120";
                      }
                      config false;
                      description
                        "Community attribute.";
                    }
                    leaf extCommunity {
                      type string {
                        length "1..300";
                      }
                      config false;
                      description
                        "Extended community attribute.";
                    }
                    leaf from {
                      type inet:ip-address-no-zone;
                      config false;
                      description
                        "Source peer that sends a route.";
                    }
                    leaf ifName {
                      type pub-type:ifName;
                      config false;
                      description
                        "Name of the outbound interface of a route.";
                    }
                    leaf originator {
                      type inet:ip-address-no-zone;
                      config false;
                      description
                        "Router ID of the route initiator.";
                    }
                    leaf clusterList {
                      type string {
                        length "1..300";
                      }
                      config false;
                      description
                        "List of cluster IDs.";
                    }
                    leaf remoteRouteId {
                      type inet:ipv4-address-no-zone;
                      config false;
                      description
                        "Router ID of a peer.";
                    }
                    leaf relayNexthop {
                      type inet:ip-address-no-zone;
                      config false;
                      description
                        "Next hop to which a route is iterated.";
                    }
                    leaf relaytnlName {
                      type string {
                        length "1..64";
                      }
                      config false;
                      description
                        "Name of a tunnel to which a route is iterated.";
                    }
                    leaf inLabel {
                      type uint32 {
                        range "0..4294967295";
                      }
                      config false;
                      description
                        "In-label.";
                    }
                    leaf outLabel {
                      type uint32 {
                        range "0..4294967295";
                      }
                      config false;
                      description
                        "Out-label.";
                    }
                    leaf ngRouteType {
                      type string {
                        length "1..50";
                      }
                      config false;
                      description
                        "Route type.";
                    }
                    leaf routeTypeFlag {
                      type pub-type:bits32 {
                        ext:masklen 32;
                          ext:bit "ibgp" {
                            position 0;
                          }
                          ext:bit "ebgp" {
                            position 1;
                          }
                          ext:bit "network" {
                            position 2;
                          }
                          ext:bit "import" {
                            position 3;
                          }
                          ext:bit "auto-summary" {
                            position 4;
                          }
                          ext:bit "aggregate" {
                            position 5;
                          }
                          ext:bit "cpri" {
                            position 6;
                          }
                          ext:bit "pcri" {
                            position 7;
                          }
                          ext:bit "suppressed" {
                            position 8;
                          }
                          ext:bit "NHP-EMPTY" {
                            position 9;
                          }
                          ext:bit "NO-ADV" {
                            position 10;
                          }
                          ext:bit "local_cross" {
                            position 11;
                          }
                          ext:bit "remote_cross" {
                            position 12;
                          }
                          ext:bit "VD-BGP" {
                            position 13;
                          }
                          ext:bit "PATH_LOCAL" {
                            position 14;
                          }
                          ext:bit "PATH_GATEWAY" {
                            position 15;
                          }
                          ext:bit "policy_nopass" {
                            position 16;
                          }
                          ext:bit "supprenet" {
                            position 17;
                          }
                          ext:bit "dampened" {
                            position 18;
                          }
                          ext:bit "history" {
                            position 19;
                          }
                          ext:bit "select" {
                            position 20;
                          }
                          ext:bit "best" {
                            position 21;
                          }
                          ext:bit "backup" {
                            position 22;
                          }
                          ext:bit "attr_change" {
                            position 23;
                          }
                          ext:bit "NHLFE_CREATED" {
                            position 24;
                          }
                          ext:bit "ILM_CREATED" {
                            position 25;
                          }
                          ext:bit "NEXTHOP_CHANGE" {
                            position 26;
                          }
                          ext:bit "Invaild" {
                            position 27;
                          }
                          ext:bit "SOURCE_CHANGE" {
                            position 28;
                          }
                          ext:bit "IN_SELECTEDQ" {
                            position 29;
                          }
                          ext:bit "EXITIF_ERROR" {
                            position 30;
                          }
                          ext:bit "GROUP_HEAD" {
                            position 31;
                          }
                      }
                      config false;
                      description
                        "Route type.";
                    }
                    leaf ngAsIpString {
                      type string {
                        length "1..300";
                      }
                      config false;
                      description
                        "Ng route prefix information.";
                    }
                    leaf advNextHop {
                      type inet:ip-address-no-zone;
                      config false;
                      description
                        "Next hop of an BGP.";
                    }
                  }
                }
                container peerNgRevRtTable5s {
                  config false;
                  description
                    "List of displayed BGP Ng Rev route type 5 information.";
                  list peerNgRevRtTable5 {
                    when "not(../../../../afType!='mvpn' and ../../../../afType!='mvpnv6')";
                    key "ngNlri rd from ngRouteType routeTypeFlag";
                    config false;
                    description
                      "Information about BGP Ng Rev routes type 5.";
                    leaf ngNlri {
                      type inet:ipv4-address-no-zone;
                      config false;
                      description
                        "Prefix of a BGP route.";
                    }
                    leaf imTableId {
                      type uint32 {
                        range "0..4294967295";
                      }
                      config false;
                      description
                        "ID of the routing table to which routes are imported.";
                    }
                    leaf nexthop {
                      type inet:ip-address-no-zone;
                      config false;
                      description
                        "Next hop address to which packets are forwarded.";
                    }
                    leaf locPrf {
                      type uint32 {
                        range "0..4294967295";
                      }
                      config false;
                      description
                        "Local-preference.";
                    }
                    leaf prefVal {
                      type uint32 {
                        range "0..4294967295";
                      }
                      config false;
                      description
                        "Preferred value of a protocol.";
                    }
                    leaf prefrence {
                      type uint8 {
                        range "0..255";
                      }
                      config false;
                      description
                        "Priority of BGP routes.";
                    }
                    leaf pathAs {
                      type string {
                        length "1..300";
                      }
                      config false;
                      description
                        "List of the AS_Paths that packets pass through.";
                    }
                    leaf origin {
                      type bgpcommOrigin;
                      config false;
                      description
                        "Route origin.";
                    }
                    leaf med {
                      type uint32 {
                        range "0..4294967295";
                      }
                      config false;
                      description
                        "Route MED.";
                    }
                    leaf flagString {
                      type string {
                        length "1..100";
                      }
                      config false;
                      description
                        "Route flag that contains a string of characters.";
                    }
                    leaf rd {
                      type string {
                        length "1..22";
                      }
                      config false;
                      description
                        "Route distinguisher.";
                    }
                    leaf rtWorseReason {
                      type string {
                        length "1..50";
                      }
                      config false;
                      description
                        "Reason why a route is not selected.";
                    }
                    leaf peerString {
                      type string {
                        length "1..300";
                      }
                      config false;
                      description
                        "List of route sending peers.";
                    }
                    leaf time {
                      type uint32 {
                        range "0..4294967295";
                      }
                      config false;
                      description
                        "Time stamp of a route.";
                    }
                    leaf community {
                      type string {
                        length "1..120";
                      }
                      config false;
                      description
                        "Community attribute.";
                    }
                    leaf extCommunity {
                      type string {
                        length "1..300";
                      }
                      config false;
                      description
                        "Extended community attribute.";
                    }
                    leaf from {
                      type inet:ip-address-no-zone;
                      config false;
                      description
                        "Source peer that sends a route.";
                    }
                    leaf ifName {
                      type pub-type:ifName;
                      config false;
                      description
                        "Name of the outbound interface of a route.";
                    }
                    leaf originator {
                      type inet:ip-address-no-zone;
                      config false;
                      description
                        "Router ID of the route initiator.";
                    }
                    leaf clusterList {
                      type string {
                        length "1..300";
                      }
                      config false;
                      description
                        "List of cluster IDs.";
                    }
                    leaf remoteRouteId {
                      type inet:ipv4-address-no-zone;
                      config false;
                      description
                        "Router ID of a peer.";
                    }
                    leaf relayNexthop {
                      type inet:ip-address-no-zone;
                      config false;
                      description
                        "Next hop to which a route is iterated.";
                    }
                    leaf relaytnlName {
                      type string {
                        length "1..64";
                      }
                      config false;
                      description
                        "Name of a tunnel to which a route is iterated.";
                    }
                    leaf inLabel {
                      type uint32 {
                        range "0..4294967295";
                      }
                      config false;
                      description
                        "In-label.";
                    }
                    leaf outLabel {
                      type uint32 {
                        range "0..4294967295";
                      }
                      config false;
                      description
                        "Out-label.";
                    }
                    leaf ngRouteType {
                      type string {
                        length "1..50";
                      }
                      config false;
                      description
                        "Route type.";
                    }
                    leaf routeTypeFlag {
                      type pub-type:bits32 {
                        ext:masklen 32;
                          ext:bit "ibgp" {
                            position 0;
                          }
                          ext:bit "ebgp" {
                            position 1;
                          }
                          ext:bit "network" {
                            position 2;
                          }
                          ext:bit "import" {
                            position 3;
                          }
                          ext:bit "auto-summary" {
                            position 4;
                          }
                          ext:bit "aggregate" {
                            position 5;
                          }
                          ext:bit "cpri" {
                            position 6;
                          }
                          ext:bit "pcri" {
                            position 7;
                          }
                          ext:bit "suppressed" {
                            position 8;
                          }
                          ext:bit "NHP-EMPTY" {
                            position 9;
                          }
                          ext:bit "NO-ADV" {
                            position 10;
                          }
                          ext:bit "local_cross" {
                            position 11;
                          }
                          ext:bit "remote_cross" {
                            position 12;
                          }
                          ext:bit "VD-BGP" {
                            position 13;
                          }
                          ext:bit "PATH_LOCAL" {
                            position 14;
                          }
                          ext:bit "PATH_GATEWAY" {
                            position 15;
                          }
                          ext:bit "policy_nopass" {
                            position 16;
                          }
                          ext:bit "supprenet" {
                            position 17;
                          }
                          ext:bit "dampened" {
                            position 18;
                          }
                          ext:bit "history" {
                            position 19;
                          }
                          ext:bit "select" {
                            position 20;
                          }
                          ext:bit "best" {
                            position 21;
                          }
                          ext:bit "backup" {
                            position 22;
                          }
                          ext:bit "attr_change" {
                            position 23;
                          }
                          ext:bit "NHLFE_CREATED" {
                            position 24;
                          }
                          ext:bit "ILM_CREATED" {
                            position 25;
                          }
                          ext:bit "NEXTHOP_CHANGE" {
                            position 26;
                          }
                          ext:bit "Invaild" {
                            position 27;
                          }
                          ext:bit "SOURCE_CHANGE" {
                            position 28;
                          }
                          ext:bit "IN_SELECTEDQ" {
                            position 29;
                          }
                          ext:bit "EXITIF_ERROR" {
                            position 30;
                          }
                          ext:bit "GROUP_HEAD" {
                            position 31;
                          }
                      }
                      config false;
                      description
                        "Route type.";
                    }
                    leaf ngAsIpString {
                      type string {
                        length "1..300";
                      }
                      config false;
                      description
                        "Ng route prefix information.";
                    }
                    leaf advNextHop {
                      type inet:ip-address-no-zone;
                      config false;
                      description
                        "Next hop of an BGP.";
                    }
                  }
                }
                container peerNgAdvRtTable5s {
                  config false;
                  description
                    "List of displayed BGP Ng Adv route type 5 information.";
                  list peerNgAdvRtTable5 {
                    when "not(../../../../afType!='mvpn' and ../../../../afType!='mvpnv6')";
                    key "ngNlri rd from ngRouteType routeTypeFlag";
                    config false;
                    description
                      "Information about BGP Ng Adv routes type 5.";
                    leaf ngNlri {
                      type inet:ipv4-address-no-zone;
                      config false;
                      description
                        "Prefix of a BGP route.";
                    }
                    leaf imTableId {
                      type uint32 {
                        range "0..4294967295";
                      }
                      config false;
                      description
                        "ID of the routing table to which routes are imported.";
                    }
                    leaf nexthop {
                      type inet:ip-address-no-zone;
                      config false;
                      description
                        "Next hop address to which packets are forwarded.";
                    }
                    leaf locPrf {
                      type uint32 {
                        range "0..4294967295";
                      }
                      config false;
                      description
                        "Local-preference.";
                    }
                    leaf prefVal {
                      type uint32 {
                        range "0..4294967295";
                      }
                      config false;
                      description
                        "Preferred value of a protocol.";
                    }
                    leaf prefrence {
                      type uint8 {
                        range "0..255";
                      }
                      config false;
                      description
                        "Priority of BGP routes.";
                    }
                    leaf pathAs {
                      type string {
                        length "1..300";
                      }
                      config false;
                      description
                        "List of the AS_Paths that packets pass through.";
                    }
                    leaf origin {
                      type bgpcommOrigin;
                      config false;
                      description
                        "Route origin.";
                    }
                    leaf med {
                      type uint32 {
                        range "0..4294967295";
                      }
                      config false;
                      description
                        "Route MED.";
                    }
                    leaf flagString {
                      type string {
                        length "1..100";
                      }
                      config false;
                      description
                        "Route flag that contains a string of characters.";
                    }
                    leaf rd {
                      type string {
                        length "1..22";
                      }
                      config false;
                      description
                        "Route distinguisher.";
                    }
                    leaf rtWorseReason {
                      type string {
                        length "1..50";
                      }
                      config false;
                      description
                        "Reason why a route is not selected.";
                    }
                    leaf peerString {
                      type string {
                        length "1..300";
                      }
                      config false;
                      description
                        "List of route sending peers.";
                    }
                    leaf time {
                      type uint32 {
                        range "0..4294967295";
                      }
                      config false;
                      description
                        "Time stamp of a route.";
                    }
                    leaf community {
                      type string {
                        length "1..120";
                      }
                      config false;
                      description
                        "Community attribute.";
                    }
                    leaf extCommunity {
                      type string {
                        length "1..300";
                      }
                      config false;
                      description
                        "Extended community attribute.";
                    }
                    leaf from {
                      type inet:ip-address-no-zone;
                      config false;
                      description
                        "Source peer that sends a route.";
                    }
                    leaf ifName {
                      type pub-type:ifName;
                      config false;
                      description
                        "Name of the outbound interface of a route.";
                    }
                    leaf originator {
                      type inet:ip-address-no-zone;
                      config false;
                      description
                        "Router ID of the route initiator.";
                    }
                    leaf clusterList {
                      type string {
                        length "1..300";
                      }
                      config false;
                      description
                        "List of cluster IDs.";
                    }
                    leaf remoteRouteId {
                      type inet:ipv4-address-no-zone;
                      config false;
                      description
                        "Router ID of a peer.";
                    }
                    leaf relayNexthop {
                      type inet:ip-address-no-zone;
                      config false;
                      description
                        "Next hop to which a route is iterated.";
                    }
                    leaf relaytnlName {
                      type string {
                        length "1..64";
                      }
                      config false;
                      description
                        "Name of a tunnel to which a route is iterated.";
                    }
                    leaf inLabel {
                      type uint32 {
                        range "0..4294967295";
                      }
                      config false;
                      description
                        "In-label.";
                    }
                    leaf outLabel {
                      type uint32 {
                        range "0..4294967295";
                      }
                      config false;
                      description
                        "Out-label.";
                    }
                    leaf ngRouteType {
                      type string {
                        length "1..50";
                      }
                      config false;
                      description
                        "Route type.";
                    }
                    leaf routeTypeFlag {
                      type pub-type:bits32 {
                        ext:masklen 32;
                          ext:bit "ibgp" {
                            position 0;
                          }
                          ext:bit "ebgp" {
                            position 1;
                          }
                          ext:bit "network" {
                            position 2;
                          }
                          ext:bit "import" {
                            position 3;
                          }
                          ext:bit "auto-summary" {
                            position 4;
                          }
                          ext:bit "aggregate" {
                            position 5;
                          }
                          ext:bit "cpri" {
                            position 6;
                          }
                          ext:bit "pcri" {
                            position 7;
                          }
                          ext:bit "suppressed" {
                            position 8;
                          }
                          ext:bit "NHP-EMPTY" {
                            position 9;
                          }
                          ext:bit "NO-ADV" {
                            position 10;
                          }
                          ext:bit "local_cross" {
                            position 11;
                          }
                          ext:bit "remote_cross" {
                            position 12;
                          }
                          ext:bit "VD-BGP" {
                            position 13;
                          }
                          ext:bit "PATH_LOCAL" {
                            position 14;
                          }
                          ext:bit "PATH_GATEWAY" {
                            position 15;
                          }
                          ext:bit "policy_nopass" {
                            position 16;
                          }
                          ext:bit "supprenet" {
                            position 17;
                          }
                          ext:bit "dampened" {
                            position 18;
                          }
                          ext:bit "history" {
                            position 19;
                          }
                          ext:bit "select" {
                            position 20;
                          }
                          ext:bit "best" {
                            position 21;
                          }
                          ext:bit "backup" {
                            position 22;
                          }
                          ext:bit "attr_change" {
                            position 23;
                          }
                          ext:bit "NHLFE_CREATED" {
                            position 24;
                          }
                          ext:bit "ILM_CREATED" {
                            position 25;
                          }
                          ext:bit "NEXTHOP_CHANGE" {
                            position 26;
                          }
                          ext:bit "Invaild" {
                            position 27;
                          }
                          ext:bit "SOURCE_CHANGE" {
                            position 28;
                          }
                          ext:bit "IN_SELECTEDQ" {
                            position 29;
                          }
                          ext:bit "EXITIF_ERROR" {
                            position 30;
                          }
                          ext:bit "GROUP_HEAD" {
                            position 31;
                          }
                      }
                      config false;
                      description
                        "Route type.";
                    }
                    leaf ngAsIpString {
                      type string {
                        length "1..300";
                      }
                      config false;
                      description
                        "Ng route prefix information.";
                    }
                    leaf advNextHop {
                      type inet:ip-address-no-zone;
                      config false;
                      description
                        "Next hop of an BGP.";
                    }
                  }
                }
                container peerNgRevRtTable6s {
                  config false;
                  description
                    "List of displayed BGP Ng Rev route type 6 information.";
                  list peerNgRevRtTable6 {
                    when "not(../../../../afType!='mvpn' and ../../../../afType!='mvpnv6')";
                    key "ngNlri rd from ngRouteType routeTypeFlag";
                    config false;
                    description
                      "Information about BGP Ng Rev routes type 6.";
                    leaf ngNlri {
                      type inet:ipv4-address-no-zone;
                      config false;
                      description
                        "Prefix of a BGP route.";
                    }
                    leaf imTableId {
                      type uint32 {
                        range "0..4294967295";
                      }
                      config false;
                      description
                        "ID of the routing table to which routes are imported.";
                    }
                    leaf nexthop {
                      type inet:ip-address-no-zone;
                      config false;
                      description
                        "Next hop address to which packets are forwarded.";
                    }
                    leaf locPrf {
                      type uint32 {
                        range "0..4294967295";
                      }
                      config false;
                      description
                        "Local-preference.";
                    }
                    leaf prefVal {
                      type uint32 {
                        range "0..4294967295";
                      }
                      config false;
                      description
                        "Preferred value of a protocol.";
                    }
                    leaf prefrence {
                      type uint8 {
                        range "0..255";
                      }
                      config false;
                      description
                        "Priority of BGP routes.";
                    }
                    leaf pathAs {
                      type string {
                        length "1..300";
                      }
                      config false;
                      description
                        "List of the AS_Paths that packets pass through.";
                    }
                    leaf origin {
                      type bgpcommOrigin;
                      config false;
                      description
                        "Route origin.";
                    }
                    leaf med {
                      type uint32 {
                        range "0..4294967295";
                      }
                      config false;
                      description
                        "Route MED.";
                    }
                    leaf flagString {
                      type string {
                        length "1..100";
                      }
                      config false;
                      description
                        "Route flag that contains a string of characters.";
                    }
                    leaf rd {
                      type string {
                        length "1..22";
                      }
                      config false;
                      description
                        "Route distinguisher.";
                    }
                    leaf rtWorseReason {
                      type string {
                        length "1..50";
                      }
                      config false;
                      description
                        "Reason why a route is not selected.";
                    }
                    leaf peerString {
                      type string {
                        length "1..300";
                      }
                      config false;
                      description
                        "List of route sending peers.";
                    }
                    leaf time {
                      type uint32 {
                        range "0..4294967295";
                      }
                      config false;
                      description
                        "Time stamp of a route.";
                    }
                    leaf community {
                      type string {
                        length "1..120";
                      }
                      config false;
                      description
                        "Community attribute.";
                    }
                    leaf extCommunity {
                      type string {
                        length "1..300";
                      }
                      config false;
                      description
                        "Extended community attribute.";
                    }
                    leaf from {
                      type inet:ip-address-no-zone;
                      config false;
                      description
                        "Source peer that sends a route.";
                    }
                    leaf ifName {
                      type pub-type:ifName;
                      config false;
                      description
                        "Name of the outbound interface of a route.";
                    }
                    leaf originator {
                      type inet:ip-address-no-zone;
                      config false;
                      description
                        "Router ID of the route initiator.";
                    }
                    leaf clusterList {
                      type string {
                        length "1..300";
                      }
                      config false;
                      description
                        "List of cluster IDs.";
                    }
                    leaf remoteRouteId {
                      type inet:ipv4-address-no-zone;
                      config false;
                      description
                        "Router ID of a peer.";
                    }
                    leaf relayNexthop {
                      type inet:ip-address-no-zone;
                      config false;
                      description
                        "Next hop to which a route is iterated.";
                    }
                    leaf relaytnlName {
                      type string {
                        length "1..64";
                      }
                      config false;
                      description
                        "Name of a tunnel to which a route is iterated.";
                    }
                    leaf inLabel {
                      type uint32 {
                        range "0..4294967295";
                      }
                      config false;
                      description
                        "In-label.";
                    }
                    leaf outLabel {
                      type uint32 {
                        range "0..4294967295";
                      }
                      config false;
                      description
                        "Out-label.";
                    }
                    leaf ngRouteType {
                      type string {
                        length "1..50";
                      }
                      config false;
                      description
                        "Route type.";
                    }
                    leaf routeTypeFlag {
                      type pub-type:bits32 {
                        ext:masklen 32;
                          ext:bit "ibgp" {
                            position 0;
                          }
                          ext:bit "ebgp" {
                            position 1;
                          }
                          ext:bit "network" {
                            position 2;
                          }
                          ext:bit "import" {
                            position 3;
                          }
                          ext:bit "auto-summary" {
                            position 4;
                          }
                          ext:bit "aggregate" {
                            position 5;
                          }
                          ext:bit "cpri" {
                            position 6;
                          }
                          ext:bit "pcri" {
                            position 7;
                          }
                          ext:bit "suppressed" {
                            position 8;
                          }
                          ext:bit "NHP-EMPTY" {
                            position 9;
                          }
                          ext:bit "NO-ADV" {
                            position 10;
                          }
                          ext:bit "local_cross" {
                            position 11;
                          }
                          ext:bit "remote_cross" {
                            position 12;
                          }
                          ext:bit "VD-BGP" {
                            position 13;
                          }
                          ext:bit "PATH_LOCAL" {
                            position 14;
                          }
                          ext:bit "PATH_GATEWAY" {
                            position 15;
                          }
                          ext:bit "policy_nopass" {
                            position 16;
                          }
                          ext:bit "supprenet" {
                            position 17;
                          }
                          ext:bit "dampened" {
                            position 18;
                          }
                          ext:bit "history" {
                            position 19;
                          }
                          ext:bit "select" {
                            position 20;
                          }
                          ext:bit "best" {
                            position 21;
                          }
                          ext:bit "backup" {
                            position 22;
                          }
                          ext:bit "attr_change" {
                            position 23;
                          }
                          ext:bit "NHLFE_CREATED" {
                            position 24;
                          }
                          ext:bit "ILM_CREATED" {
                            position 25;
                          }
                          ext:bit "NEXTHOP_CHANGE" {
                            position 26;
                          }
                          ext:bit "Invaild" {
                            position 27;
                          }
                          ext:bit "SOURCE_CHANGE" {
                            position 28;
                          }
                          ext:bit "IN_SELECTEDQ" {
                            position 29;
                          }
                          ext:bit "EXITIF_ERROR" {
                            position 30;
                          }
                          ext:bit "GROUP_HEAD" {
                            position 31;
                          }
                      }
                      config false;
                      description
                        "Route type.";
                    }
                    leaf ngAsIpString {
                      type string {
                        length "1..300";
                      }
                      config false;
                      description
                        "Ng route prefix information.";
                    }
                    leaf advNextHop {
                      type inet:ip-address-no-zone;
                      config false;
                      description
                        "Next hop of an BGP.";
                    }
                  }
                }
                container peerNgAdvRtTable6s {
                  config false;
                  description
                    "List of displayed BGP Ng Adv route type 6 information.";
                  list peerNgAdvRtTable6 {
                    when "not(../../../../afType!='mvpn' and ../../../../afType!='mvpnv6')";
                    key "ngNlri rd from ngRouteType routeTypeFlag";
                    config false;
                    description
                      "Information about BGP Ng Adv routes type 6.";
                    leaf ngNlri {
                      type inet:ipv4-address-no-zone;
                      config false;
                      description
                        "Prefix of a BGP route.";
                    }
                    leaf imTableId {
                      type uint32 {
                        range "0..4294967295";
                      }
                      config false;
                      description
                        "ID of the routing table to which routes are imported.";
                    }
                    leaf nexthop {
                      type inet:ip-address-no-zone;
                      config false;
                      description
                        "Next hop address to which packets are forwarded.";
                    }
                    leaf locPrf {
                      type uint32 {
                        range "0..4294967295";
                      }
                      config false;
                      description
                        "Local-preference.";
                    }
                    leaf prefVal {
                      type uint32 {
                        range "0..4294967295";
                      }
                      config false;
                      description
                        "Preferred value of a protocol.";
                    }
                    leaf prefrence {
                      type uint8 {
                        range "0..255";
                      }
                      config false;
                      description
                        "Priority of BGP routes.";
                    }
                    leaf pathAs {
                      type string {
                        length "1..300";
                      }
                      config false;
                      description
                        "List of the AS_Paths that packets pass through.";
                    }
                    leaf origin {
                      type bgpcommOrigin;
                      config false;
                      description
                        "Route origin.";
                    }
                    leaf med {
                      type uint32 {
                        range "0..4294967295";
                      }
                      config false;
                      description
                        "Route MED.";
                    }
                    leaf flagString {
                      type string {
                        length "1..100";
                      }
                      config false;
                      description
                        "Route flag that contains a string of characters.";
                    }
                    leaf rd {
                      type string {
                        length "1..22";
                      }
                      config false;
                      description
                        "Route distinguisher.";
                    }
                    leaf rtWorseReason {
                      type string {
                        length "1..50";
                      }
                      config false;
                      description
                        "Reason why a route is not selected.";
                    }
                    leaf peerString {
                      type string {
                        length "1..300";
                      }
                      config false;
                      description
                        "List of route sending peers.";
                    }
                    leaf time {
                      type uint32 {
                        range "0..4294967295";
                      }
                      config false;
                      description
                        "Time stamp of a route.";
                    }
                    leaf community {
                      type string {
                        length "1..120";
                      }
                      config false;
                      description
                        "Community attribute.";
                    }
                    leaf extCommunity {
                      type string {
                        length "1..300";
                      }
                      config false;
                      description
                        "Extended community attribute.";
                    }
                    leaf from {
                      type inet:ip-address-no-zone;
                      config false;
                      description
                        "Source peer that sends a route.";
                    }
                    leaf ifName {
                      type pub-type:ifName;
                      config false;
                      description
                        "Name of the outbound interface of a route.";
                    }
                    leaf originator {
                      type inet:ip-address-no-zone;
                      config false;
                      description
                        "Router ID of the route initiator.";
                    }
                    leaf clusterList {
                      type string {
                        length "1..300";
                      }
                      config false;
                      description
                        "List of cluster IDs.";
                    }
                    leaf remoteRouteId {
                      type inet:ipv4-address-no-zone;
                      config false;
                      description
                        "Router ID of a peer.";
                    }
                    leaf relayNexthop {
                      type inet:ip-address-no-zone;
                      config false;
                      description
                        "Next hop to which a route is iterated.";
                    }
                    leaf relaytnlName {
                      type string {
                        length "1..64";
                      }
                      config false;
                      description
                        "Name of a tunnel to which a route is iterated.";
                    }
                    leaf inLabel {
                      type uint32 {
                        range "0..4294967295";
                      }
                      config false;
                      description
                        "In-label.";
                    }
                    leaf outLabel {
                      type uint32 {
                        range "0..4294967295";
                      }
                      config false;
                      description
                        "Out-label.";
                    }
                    leaf ngRouteType {
                      type string {
                        length "1..50";
                      }
                      config false;
                      description
                        "Route type.";
                    }
                    leaf routeTypeFlag {
                      type pub-type:bits32 {
                        ext:masklen 32;
                          ext:bit "ibgp" {
                            position 0;
                          }
                          ext:bit "ebgp" {
                            position 1;
                          }
                          ext:bit "network" {
                            position 2;
                          }
                          ext:bit "import" {
                            position 3;
                          }
                          ext:bit "auto-summary" {
                            position 4;
                          }
                          ext:bit "aggregate" {
                            position 5;
                          }
                          ext:bit "cpri" {
                            position 6;
                          }
                          ext:bit "pcri" {
                            position 7;
                          }
                          ext:bit "suppressed" {
                            position 8;
                          }
                          ext:bit "NHP-EMPTY" {
                            position 9;
                          }
                          ext:bit "NO-ADV" {
                            position 10;
                          }
                          ext:bit "local_cross" {
                            position 11;
                          }
                          ext:bit "remote_cross" {
                            position 12;
                          }
                          ext:bit "VD-BGP" {
                            position 13;
                          }
                          ext:bit "PATH_LOCAL" {
                            position 14;
                          }
                          ext:bit "PATH_GATEWAY" {
                            position 15;
                          }
                          ext:bit "policy_nopass" {
                            position 16;
                          }
                          ext:bit "supprenet" {
                            position 17;
                          }
                          ext:bit "dampened" {
                            position 18;
                          }
                          ext:bit "history" {
                            position 19;
                          }
                          ext:bit "select" {
                            position 20;
                          }
                          ext:bit "best" {
                            position 21;
                          }
                          ext:bit "backup" {
                            position 22;
                          }
                          ext:bit "attr_change" {
                            position 23;
                          }
                          ext:bit "NHLFE_CREATED" {
                            position 24;
                          }
                          ext:bit "ILM_CREATED" {
                            position 25;
                          }
                          ext:bit "NEXTHOP_CHANGE" {
                            position 26;
                          }
                          ext:bit "Invaild" {
                            position 27;
                          }
                          ext:bit "SOURCE_CHANGE" {
                            position 28;
                          }
                          ext:bit "IN_SELECTEDQ" {
                            position 29;
                          }
                          ext:bit "EXITIF_ERROR" {
                            position 30;
                          }
                          ext:bit "GROUP_HEAD" {
                            position 31;
                          }
                      }
                      config false;
                      description
                        "Route type.";
                    }
                    leaf ngAsIpString {
                      type string {
                        length "1..300";
                      }
                      config false;
                      description
                        "Ng route prefix information.";
                    }
                    leaf advNextHop {
                      type inet:ip-address-no-zone;
                      config false;
                      description
                        "Next hop of an BGP.";
                    }
                  }
                }
                container peerNgRevRtTable7s {
                  config false;
                  description
                    "List of displayed BGP Ng Rev route type 7 information.";
                  list peerNgRevRtTable7 {
                    when "not(../../../../afType!='mvpn' and ../../../../afType!='mvpnv6')";
                    key "ngNlri rd from ngRouteType routeTypeFlag";
                    config false;
                    description
                      "Information about BGP Ng Rev routes type 7.";
                    leaf ngNlri {
                      type inet:ipv4-address-no-zone;
                      config false;
                      description
                        "Prefix of a BGP route.";
                    }
                    leaf imTableId {
                      type uint32 {
                        range "0..4294967295";
                      }
                      config false;
                      description
                        "ID of the routing table to which routes are imported.";
                    }
                    leaf nexthop {
                      type inet:ip-address-no-zone;
                      config false;
                      description
                        "Next hop address to which packets are forwarded.";
                    }
                    leaf locPrf {
                      type uint32 {
                        range "0..4294967295";
                      }
                      config false;
                      description
                        "Local-preference.";
                    }
                    leaf prefVal {
                      type uint32 {
                        range "0..4294967295";
                      }
                      config false;
                      description
                        "Preferred value of a protocol.";
                    }
                    leaf prefrence {
                      type uint8 {
                        range "0..255";
                      }
                      config false;
                      description
                        "Priority of BGP routes.";
                    }
                    leaf pathAs {
                      type string {
                        length "1..300";
                      }
                      config false;
                      description
                        "List of the AS_Paths that packets pass through.";
                    }
                    leaf origin {
                      type bgpcommOrigin;
                      config false;
                      description
                        "Route origin.";
                    }
                    leaf med {
                      type uint32 {
                        range "0..4294967295";
                      }
                      config false;
                      description
                        "Route MED.";
                    }
                    leaf flagString {
                      type string {
                        length "1..100";
                      }
                      config false;
                      description
                        "Route flag that contains a string of characters.";
                    }
                    leaf rd {
                      type string {
                        length "1..22";
                      }
                      config false;
                      description
                        "Route distinguisher.";
                    }
                    leaf rtWorseReason {
                      type string {
                        length "1..50";
                      }
                      config false;
                      description
                        "Reason why a route is not selected.";
                    }
                    leaf peerString {
                      type string {
                        length "1..300";
                      }
                      config false;
                      description
                        "List of route sending peers.";
                    }
                    leaf time {
                      type uint32 {
                        range "0..4294967295";
                      }
                      config false;
                      description
                        "Time stamp of a route.";
                    }
                    leaf community {
                      type string {
                        length "1..120";
                      }
                      config false;
                      description
                        "Community attribute.";
                    }
                    leaf extCommunity {
                      type string {
                        length "1..300";
                      }
                      config false;
                      description
                        "Extended community attribute.";
                    }
                    leaf from {
                      type inet:ip-address-no-zone;
                      config false;
                      description
                        "Source peer that sends a route.";
                    }
                    leaf ifName {
                      type pub-type:ifName;
                      config false;
                      description
                        "Name of the outbound interface of a route.";
                    }
                    leaf originator {
                      type inet:ip-address-no-zone;
                      config false;
                      description
                        "Router ID of the route initiator.";
                    }
                    leaf clusterList {
                      type string {
                        length "1..300";
                      }
                      config false;
                      description
                        "List of cluster IDs.";
                    }
                    leaf remoteRouteId {
                      type inet:ipv4-address-no-zone;
                      config false;
                      description
                        "Router ID of a peer.";
                    }
                    leaf relayNexthop {
                      type inet:ip-address-no-zone;
                      config false;
                      description
                        "Next hop to which a route is iterated.";
                    }
                    leaf relaytnlName {
                      type string {
                        length "1..64";
                      }
                      config false;
                      description
                        "Name of a tunnel to which a route is iterated.";
                    }
                    leaf inLabel {
                      type uint32 {
                        range "0..4294967295";
                      }
                      config false;
                      description
                        "In-label.";
                    }
                    leaf outLabel {
                      type uint32 {
                        range "0..4294967295";
                      }
                      config false;
                      description
                        "Out-label.";
                    }
                    leaf ngRouteType {
                      type string {
                        length "1..50";
                      }
                      config false;
                      description
                        "Route type.";
                    }
                    leaf routeTypeFlag {
                      type pub-type:bits32 {
                        ext:masklen 32;
                          ext:bit "ibgp" {
                            position 0;
                          }
                          ext:bit "ebgp" {
                            position 1;
                          }
                          ext:bit "network" {
                            position 2;
                          }
                          ext:bit "import" {
                            position 3;
                          }
                          ext:bit "auto-summary" {
                            position 4;
                          }
                          ext:bit "aggregate" {
                            position 5;
                          }
                          ext:bit "cpri" {
                            position 6;
                          }
                          ext:bit "pcri" {
                            position 7;
                          }
                          ext:bit "suppressed" {
                            position 8;
                          }
                          ext:bit "NHP-EMPTY" {
                            position 9;
                          }
                          ext:bit "NO-ADV" {
                            position 10;
                          }
                          ext:bit "local_cross" {
                            position 11;
                          }
                          ext:bit "remote_cross" {
                            position 12;
                          }
                          ext:bit "VD-BGP" {
                            position 13;
                          }
                          ext:bit "PATH_LOCAL" {
                            position 14;
                          }
                          ext:bit "PATH_GATEWAY" {
                            position 15;
                          }
                          ext:bit "policy_nopass" {
                            position 16;
                          }
                          ext:bit "supprenet" {
                            position 17;
                          }
                          ext:bit "dampened" {
                            position 18;
                          }
                          ext:bit "history" {
                            position 19;
                          }
                          ext:bit "select" {
                            position 20;
                          }
                          ext:bit "best" {
                            position 21;
                          }
                          ext:bit "backup" {
                            position 22;
                          }
                          ext:bit "attr_change" {
                            position 23;
                          }
                          ext:bit "NHLFE_CREATED" {
                            position 24;
                          }
                          ext:bit "ILM_CREATED" {
                            position 25;
                          }
                          ext:bit "NEXTHOP_CHANGE" {
                            position 26;
                          }
                          ext:bit "Invaild" {
                            position 27;
                          }
                          ext:bit "SOURCE_CHANGE" {
                            position 28;
                          }
                          ext:bit "IN_SELECTEDQ" {
                            position 29;
                          }
                          ext:bit "EXITIF_ERROR" {
                            position 30;
                          }
                          ext:bit "GROUP_HEAD" {
                            position 31;
                          }
                      }
                      config false;
                      description
                        "Route type.";
                    }
                    leaf ngAsIpString {
                      type string {
                        length "1..300";
                      }
                      config false;
                      description
                        "Ng route prefix information.";
                    }
                    leaf advNextHop {
                      type inet:ip-address-no-zone;
                      config false;
                      description
                        "Next hop of an BGP.";
                    }
                  }
                }
                container peerNgAdvRtTable7s {
                  config false;
                  description
                    "List of displayed BGP Ng Adv route type 7 information.";
                  list peerNgAdvRtTable7 {
                    when "not(../../../../afType!='mvpn' and ../../../../afType!='mvpnv6')";
                    key "ngNlri rd from ngRouteType routeTypeFlag";
                    config false;
                    description
                      "Information about BGP Ng Adv routes type 7.";
                    leaf ngNlri {
                      type inet:ipv4-address-no-zone;
                      config false;
                      description
                        "Prefix of a BGP route.";
                    }
                    leaf imTableId {
                      type uint32 {
                        range "0..4294967295";
                      }
                      config false;
                      description
                        "ID of the routing table to which routes are imported.";
                    }
                    leaf nexthop {
                      type inet:ip-address-no-zone;
                      config false;
                      description
                        "Next hop address to which packets are forwarded.";
                    }
                    leaf locPrf {
                      type uint32 {
                        range "0..4294967295";
                      }
                      config false;
                      description
                        "Local-preference.";
                    }
                    leaf prefVal {
                      type uint32 {
                        range "0..4294967295";
                      }
                      config false;
                      description
                        "Preferred value of a protocol.";
                    }
                    leaf prefrence {
                      type uint8 {
                        range "0..255";
                      }
                      config false;
                      description
                        "Priority of BGP routes.";
                    }
                    leaf pathAs {
                      type string {
                        length "1..300";
                      }
                      config false;
                      description
                        "List of the AS_Paths that packets pass through.";
                    }
                    leaf origin {
                      type bgpcommOrigin;
                      config false;
                      description
                        "Route origin.";
                    }
                    leaf med {
                      type uint32 {
                        range "0..4294967295";
                      }
                      config false;
                      description
                        "Route MED.";
                    }
                    leaf flagString {
                      type string {
                        length "1..100";
                      }
                      config false;
                      description
                        "Route flag that contains a string of characters.";
                    }
                    leaf rd {
                      type string {
                        length "1..22";
                      }
                      config false;
                      description
                        "Route distinguisher.";
                    }
                    leaf rtWorseReason {
                      type string {
                        length "1..50";
                      }
                      config false;
                      description
                        "Reason why a route is not selected.";
                    }
                    leaf peerString {
                      type string {
                        length "1..300";
                      }
                      config false;
                      description
                        "List of route sending peers.";
                    }
                    leaf time {
                      type uint32 {
                        range "0..4294967295";
                      }
                      config false;
                      description
                        "Time stamp of a route.";
                    }
                    leaf community {
                      type string {
                        length "1..120";
                      }
                      config false;
                      description
                        "Community attribute.";
                    }
                    leaf extCommunity {
                      type string {
                        length "1..300";
                      }
                      config false;
                      description
                        "Extended community attribute.";
                    }
                    leaf from {
                      type inet:ip-address-no-zone;
                      config false;
                      description
                        "Source peer that sends a route.";
                    }
                    leaf ifName {
                      type pub-type:ifName;
                      config false;
                      description
                        "Name of the outbound interface of a route.";
                    }
                    leaf originator {
                      type inet:ip-address-no-zone;
                      config false;
                      description
                        "Router ID of the route initiator.";
                    }
                    leaf clusterList {
                      type string {
                        length "1..300";
                      }
                      config false;
                      description
                        "List of cluster IDs.";
                    }
                    leaf remoteRouteId {
                      type inet:ipv4-address-no-zone;
                      config false;
                      description
                        "Router ID of a peer.";
                    }
                    leaf relayNexthop {
                      type inet:ip-address-no-zone;
                      config false;
                      description
                        "Next hop to which a route is iterated.";
                    }
                    leaf relaytnlName {
                      type string {
                        length "1..64";
                      }
                      config false;
                      description
                        "Name of a tunnel to which a route is iterated.";
                    }
                    leaf inLabel {
                      type uint32 {
                        range "0..4294967295";
                      }
                      config false;
                      description
                        "In-label.";
                    }
                    leaf outLabel {
                      type uint32 {
                        range "0..4294967295";
                      }
                      config false;
                      description
                        "Out-label.";
                    }
                    leaf ngRouteType {
                      type string {
                        length "1..50";
                      }
                      config false;
                      description
                        "Route type.";
                    }
                    leaf routeTypeFlag {
                      type pub-type:bits32 {
                        ext:masklen 32;
                          ext:bit "ibgp" {
                            position 0;
                          }
                          ext:bit "ebgp" {
                            position 1;
                          }
                          ext:bit "network" {
                            position 2;
                          }
                          ext:bit "import" {
                            position 3;
                          }
                          ext:bit "auto-summary" {
                            position 4;
                          }
                          ext:bit "aggregate" {
                            position 5;
                          }
                          ext:bit "cpri" {
                            position 6;
                          }
                          ext:bit "pcri" {
                            position 7;
                          }
                          ext:bit "suppressed" {
                            position 8;
                          }
                          ext:bit "NHP-EMPTY" {
                            position 9;
                          }
                          ext:bit "NO-ADV" {
                            position 10;
                          }
                          ext:bit "local_cross" {
                            position 11;
                          }
                          ext:bit "remote_cross" {
                            position 12;
                          }
                          ext:bit "VD-BGP" {
                            position 13;
                          }
                          ext:bit "PATH_LOCAL" {
                            position 14;
                          }
                          ext:bit "PATH_GATEWAY" {
                            position 15;
                          }
                          ext:bit "policy_nopass" {
                            position 16;
                          }
                          ext:bit "supprenet" {
                            position 17;
                          }
                          ext:bit "dampened" {
                            position 18;
                          }
                          ext:bit "history" {
                            position 19;
                          }
                          ext:bit "select" {
                            position 20;
                          }
                          ext:bit "best" {
                            position 21;
                          }
                          ext:bit "backup" {
                            position 22;
                          }
                          ext:bit "attr_change" {
                            position 23;
                          }
                          ext:bit "NHLFE_CREATED" {
                            position 24;
                          }
                          ext:bit "ILM_CREATED" {
                            position 25;
                          }
                          ext:bit "NEXTHOP_CHANGE" {
                            position 26;
                          }
                          ext:bit "Invaild" {
                            position 27;
                          }
                          ext:bit "SOURCE_CHANGE" {
                            position 28;
                          }
                          ext:bit "IN_SELECTEDQ" {
                            position 29;
                          }
                          ext:bit "EXITIF_ERROR" {
                            position 30;
                          }
                          ext:bit "GROUP_HEAD" {
                            position 31;
                          }
                      }
                      config false;
                      description
                        "Route type.";
                    }
                    leaf ngAsIpString {
                      type string {
                        length "1..300";
                      }
                      config false;
                      description
                        "Ng route prefix information.";
                    }
                    leaf advNextHop {
                      type inet:ip-address-no-zone;
                      config false;
                      description
                        "Next hop of an BGP.";
                    }
                  }
                }
                container peerVpnv4McastRevRtTables {
                  config false;
                  description
                    "List of displayed Rev route information in VPNv4 Multicast address family.";
                  list peerVpnv4McastRevRtTable {
                    when "not(../../../../afType='ipv4uni' or ../../../../afType='mvpn')";
                    key "from networkPrefix prefixMask rd routeTypeFlag imTableId";
                    config false;
                    description
                      "Information about VPNv4 Multicast Rev routes.";
                    leaf from {
                      type inet:ip-address-no-zone;
                      config false;
                      description
                        "Source peer that sends a route.";
                    }
                    leaf networkPrefix {
                      type inet:ip-address-no-zone;
                      config false;
                      description
                        "BGP route prefix.";
                    }
                    leaf prefixMask {
                      type uint8;
                      config false;
                      description
                        "Prefix mask.";
                    }
                    leaf rd {
                      type string {
                        length "1..22";
                      }
                      config false;
                      description
                        "Route distinguisher.";
                    }
                    leaf routeTypeFlag {
                      type pub-type:bits32 {
                        ext:masklen 32;
                          ext:bit "ibgp" {
                            position 0;
                          }
                          ext:bit "ebgp" {
                            position 1;
                          }
                          ext:bit "network" {
                            position 2;
                          }
                          ext:bit "import" {
                            position 3;
                          }
                          ext:bit "auto-summary" {
                            position 4;
                          }
                          ext:bit "aggregate" {
                            position 5;
                          }
                          ext:bit "cpri" {
                            position 6;
                          }
                          ext:bit "pcri" {
                            position 7;
                          }
                          ext:bit "suppressed" {
                            position 8;
                          }
                          ext:bit "NHP-EMPTY" {
                            position 9;
                          }
                          ext:bit "NO-ADV" {
                            position 10;
                          }
                          ext:bit "local_cross" {
                            position 11;
                          }
                          ext:bit "remote_cross" {
                            position 12;
                          }
                          ext:bit "VD-BGP" {
                            position 13;
                          }
                          ext:bit "PATH_LOCAL" {
                            position 14;
                          }
                          ext:bit "PATH_GATEWAY" {
                            position 15;
                          }
                          ext:bit "policy_nopass" {
                            position 16;
                          }
                          ext:bit "supprenet" {
                            position 17;
                          }
                          ext:bit "dampened" {
                            position 18;
                          }
                          ext:bit "history" {
                            position 19;
                          }
                          ext:bit "select" {
                            position 20;
                          }
                          ext:bit "best" {
                            position 21;
                          }
                          ext:bit "backup" {
                            position 22;
                          }
                          ext:bit "attr_change" {
                            position 23;
                          }
                          ext:bit "NHLFE_CREATED" {
                            position 24;
                          }
                          ext:bit "ILM_CREATED" {
                            position 25;
                          }
                          ext:bit "NEXTHOP_CHANGE" {
                            position 26;
                          }
                          ext:bit "Invaild" {
                            position 27;
                          }
                          ext:bit "SOURCE_CHANGE" {
                            position 28;
                          }
                          ext:bit "IN_SELECTEDQ" {
                            position 29;
                          }
                          ext:bit "EXITIF_ERROR" {
                            position 30;
                          }
                          ext:bit "GROUP_HEAD" {
                            position 31;
                          }
                      }
                      config false;
                      description
                        "Route type.";
                    }
                    leaf imTableId {
                      type uint32 {
                        range "0..4294967295";
                      }
                      config false;
                      description
                        "ID of the routing table to which routes are imported.";
                    }
                    leaf nexthop {
                      type inet:ip-address-no-zone;
                      config false;
                      description
                        "Next hop address to which packets are forwarded.";
                    }
                    leaf locPrf {
                      type uint32 {
                        range "0..4294967295";
                      }
                      config false;
                      description
                        "Local-preference.";
                    }
                    leaf prefVal {
                      type uint32 {
                        range "0..4294967295";
                      }
                      config false;
                      description
                        "Preferred value of a protocol.";
                    }
                    leaf prefrence {
                      type uint8 {
                        range "0..255";
                      }
                      config false;
                      description
                        "Priority of BGP routes.";
                    }
                    leaf pathAs {
                      type string {
                        length "1..300";
                      }
                      config false;
                      description
                        "List of the AS_Paths that packets pass through.";
                    }
                    leaf origin {
                      type bgpcommOrigin;
                      config false;
                      description
                        "Route origin.";
                    }
                    leaf med {
                      type uint32 {
                        range "0..4294967295";
                      }
                      config false;
                      description
                        "Route MED.";
                    }
                    leaf flagString {
                      type string {
                        length "1..100";
                      }
                      config false;
                      description
                        "Route flag that contains a string of characters.";
                    }
                    leaf rtWorseReason {
                      type string {
                        length "1..50";
                      }
                      config false;
                      description
                        "Reason why a route is not selected.";
                    }
                    leaf peerString {
                      type string {
                        length "1..300";
                      }
                      config false;
                      description
                        "List of route sending peers.";
                    }
                    leaf time {
                      type uint32 {
                        range "0..4294967295";
                      }
                      config false;
                      description
                        "Time stamp of a route.";
                    }
                    leaf community {
                      type string {
                        length "1..120";
                      }
                      config false;
                      description
                        "Community attribute.";
                    }
                    leaf extCommunity {
                      type string {
                        length "1..300";
                      }
                      config false;
                      description
                        "Extended community attribute.";
                    }
                    leaf ifName {
                      type pub-type:ifName;
                      config false;
                      description
                        "Name of the outbound interface of a route.";
                    }
                    leaf originator {
                      type inet:ip-address-no-zone;
                      config false;
                      description
                        "Router ID of the route initiator.";
                    }
                    leaf clusterList {
                      type string {
                        length "1..300";
                      }
                      config false;
                      description
                        "List of cluster IDs.";
                    }
                    leaf remoteRouteId {
                      type inet:ipv4-address-no-zone;
                      config false;
                      description
                        "Router ID of a peer.";
                    }
                    leaf relayNexthop {
                      type inet:ip-address-no-zone;
                      config false;
                      description
                        "Next hop to which a route is iterated.";
                    }
                    leaf relaytnlName {
                      type string {
                        length "1..64";
                      }
                      config false;
                      description
                        "Name of a tunnel to which a route is iterated.";
                    }
                    leaf inLabel {
                      type uint32 {
                        range "0..4294967295";
                      }
                      config false;
                      description
                        "In-label.";
                    }
                    leaf outLabel {
                      type uint32 {
                        range "0..4294967295";
                      }
                      config false;
                      description
                        "Out-label.";
                    }
                    leaf advNextHop {
                      type inet:ip-address-no-zone;
                      config false;
                      description
                        "Next hop of an BGP.";
                    }
                  }
                }
                container peerVpnv4McastAdvRtTables {
                  config false;
                  description
                    "List of displayed Adv route information in VPNv4 Multicast address family.";
                  list peerVpnv4McastAdvRtTable {
                    when "not(../../../../afType='ipv4uni' or ../../../../afType='mvpn')";
                    key "from networkPrefix prefixMask rd routeTypeFlag imTableId";
                    config false;
                    description
                      "Information about VPNv4 Multicast Adv routes.";
                    leaf from {
                      type inet:ip-address-no-zone;
                      config false;
                      description
                        "Source peer that sends a route.";
                    }
                    leaf networkPrefix {
                      type inet:ip-address-no-zone;
                      config false;
                      description
                        "BGP route prefix.";
                    }
                    leaf prefixMask {
                      type uint8;
                      config false;
                      description
                        "Prefix mask.";
                    }
                    leaf rd {
                      type string {
                        length "1..22";
                      }
                      config false;
                      description
                        "Route distinguisher.";
                    }
                    leaf routeTypeFlag {
                      type pub-type:bits32 {
                        ext:masklen 32;
                          ext:bit "ibgp" {
                            position 0;
                          }
                          ext:bit "ebgp" {
                            position 1;
                          }
                          ext:bit "network" {
                            position 2;
                          }
                          ext:bit "import" {
                            position 3;
                          }
                          ext:bit "auto-summary" {
                            position 4;
                          }
                          ext:bit "aggregate" {
                            position 5;
                          }
                          ext:bit "cpri" {
                            position 6;
                          }
                          ext:bit "pcri" {
                            position 7;
                          }
                          ext:bit "suppressed" {
                            position 8;
                          }
                          ext:bit "NHP-EMPTY" {
                            position 9;
                          }
                          ext:bit "NO-ADV" {
                            position 10;
                          }
                          ext:bit "local_cross" {
                            position 11;
                          }
                          ext:bit "remote_cross" {
                            position 12;
                          }
                          ext:bit "VD-BGP" {
                            position 13;
                          }
                          ext:bit "PATH_LOCAL" {
                            position 14;
                          }
                          ext:bit "PATH_GATEWAY" {
                            position 15;
                          }
                          ext:bit "policy_nopass" {
                            position 16;
                          }
                          ext:bit "supprenet" {
                            position 17;
                          }
                          ext:bit "dampened" {
                            position 18;
                          }
                          ext:bit "history" {
                            position 19;
                          }
                          ext:bit "select" {
                            position 20;
                          }
                          ext:bit "best" {
                            position 21;
                          }
                          ext:bit "backup" {
                            position 22;
                          }
                          ext:bit "attr_change" {
                            position 23;
                          }
                          ext:bit "NHLFE_CREATED" {
                            position 24;
                          }
                          ext:bit "ILM_CREATED" {
                            position 25;
                          }
                          ext:bit "NEXTHOP_CHANGE" {
                            position 26;
                          }
                          ext:bit "Invaild" {
                            position 27;
                          }
                          ext:bit "SOURCE_CHANGE" {
                            position 28;
                          }
                          ext:bit "IN_SELECTEDQ" {
                            position 29;
                          }
                          ext:bit "EXITIF_ERROR" {
                            position 30;
                          }
                          ext:bit "GROUP_HEAD" {
                            position 31;
                          }
                      }
                      config false;
                      description
                        "Route type.";
                    }
                    leaf imTableId {
                      type uint32 {
                        range "0..4294967295";
                      }
                      config false;
                      description
                        "ID of the routing table to which routes are imported.";
                    }
                    leaf nexthop {
                      type inet:ip-address-no-zone;
                      config false;
                      description
                        "Next hop address to which packets are forwarded.";
                    }
                    leaf locPrf {
                      type uint32 {
                        range "0..4294967295";
                      }
                      config false;
                      description
                        "Local-preference.";
                    }
                    leaf prefVal {
                      type uint32 {
                        range "0..4294967295";
                      }
                      config false;
                      description
                        "Preferred value of a protocol.";
                    }
                    leaf prefrence {
                      type uint8 {
                        range "0..255";
                      }
                      config false;
                      description
                        "Priority of BGP routes.";
                    }
                    leaf pathAs {
                      type string {
                        length "1..300";
                      }
                      config false;
                      description
                        "List of the AS_Paths that packets pass through.";
                    }
                    leaf origin {
                      type bgpcommOrigin;
                      config false;
                      description
                        "Route origin.";
                    }
                    leaf med {
                      type uint32 {
                        range "0..4294967295";
                      }
                      config false;
                      description
                        "Route MED.";
                    }
                    leaf flagString {
                      type string {
                        length "1..100";
                      }
                      config false;
                      description
                        "Route flag that contains a string of characters.";
                    }
                    leaf rtWorseReason {
                      type string {
                        length "1..50";
                      }
                      config false;
                      description
                        "Reason why a route is not selected.";
                    }
                    leaf peerString {
                      type string {
                        length "1..300";
                      }
                      config false;
                      description
                        "List of route sending peers.";
                    }
                    leaf time {
                      type uint32 {
                        range "0..4294967295";
                      }
                      config false;
                      description
                        "Time stamp of a route.";
                    }
                    leaf community {
                      type string {
                        length "1..120";
                      }
                      config false;
                      description
                        "Community attribute.";
                    }
                    leaf extCommunity {
                      type string {
                        length "1..300";
                      }
                      config false;
                      description
                        "Extended community attribute.";
                    }
                    leaf ifName {
                      type pub-type:ifName;
                      config false;
                      description
                        "Name of the outbound interface of a route.";
                    }
                    leaf originator {
                      type inet:ip-address-no-zone;
                      config false;
                      description
                        "Router ID of the route initiator.";
                    }
                    leaf clusterList {
                      type string {
                        length "1..300";
                      }
                      config false;
                      description
                        "List of cluster IDs.";
                    }
                    leaf remoteRouteId {
                      type inet:ipv4-address-no-zone;
                      config false;
                      description
                        "Router ID of a peer.";
                    }
                    leaf relayNexthop {
                      type inet:ip-address-no-zone;
                      config false;
                      description
                        "Next hop to which a route is iterated.";
                    }
                    leaf relaytnlName {
                      type string {
                        length "1..64";
                      }
                      config false;
                      description
                        "Name of a tunnel to which a route is iterated.";
                    }
                    leaf inLabel {
                      type uint32 {
                        range "0..4294967295";
                      }
                      config false;
                      description
                        "In-label.";
                    }
                    leaf outLabel {
                      type uint32 {
                        range "0..4294967295";
                      }
                      config false;
                      description
                        "Out-label.";
                    }
                    leaf advNextHop {
                      type inet:ip-address-no-zone;
                      config false;
                      description
                        "Next hop of an BGP.";
                    }
                  }
                }											
              }
            }
            container importRoutes {
              when "not(../afType='ipv4vpnmcast' or ../afType='mdt' or ../afType='vpntarget' or ../afType='vpnv4flow' or ../afType='vpnv6flow')";
              description
                "List of imported routes.";
              list importRoute {
                when "not(../../afType='rpd') or ../../afType!='ipv4vpn' and ../../afType!='ipv6vpn' and ../../afType!='ipv4flow' and ../../afType!='ipv6flow' and ../../afType!='l2vpnad' and ../../afType!='mvpn' and ../../afType!='mvpnv6' and ../../afType!='evpn' and ../../afType!='ipv4vpnmcast' and ../../afType!='mdt' and ../../afType!='ls' and ../../afType!='rpd' and ../../afType!='vpntarget'";
                key "importProtocol importProcessId";
                description
                  "Route import. Routes of other protocol types can be imported by BGP. By default, BGP does not import routes of other protocol types.";
                leaf importProtocol {
                  type bgpcommImRouteProtocol;
                  must "(../../../afType='ipv6uni' and (../importProtocol='direct' or ../importProtocol='isis' or ../importProtocol='static' or ../importProtocol='ospfv3' or ../importProtocol='ripng' or ../importProtocol='unr') ) or ((not(../../../afType='ipv6uni') and (../importProtocol='direct' or ../importProtocol='ospf' or ../importProtocol='isis' or ../importProtocol='static' or ../importProtocol='rip' or ../importProtocol='unr' or ../importProtocol='op-route') ))";
                  description
                    "Routing protocol from which routes can be imported. The routing protocol can be IS-IS, OSPF, static, direct, or RIP for an IPv4 unicast address family or an IPv4 multicast address family. The routing protocol can be IS-IS, OSPFv3, static, direct, or RIPng for an IPv6 uincast address family.";
                }
                leaf importProcessId {
                  type uint32 {
                    range "0..4294967295";
                  }
                  must "../importProtocol and ((not(../importProtocol!='direct' and ../importProtocol!='static' and ../importProtocol!='unr' and ../importProtocol!='op-route') and ../importProcessId=0) or ( ../importProtocol!='direct' and ../importProtocol!='static' and ../importProtocol!='unr' and ../importProtocol!='op-route' and ../importProcessId!=0))";
                  description
                    "Process ID of an imported routing protocol. The process ID must be specified if the imported routing protocol is RIP, OSPF, RIPng, or OSPFv3.";
                }
                leaf importRoutePolicy {
                  type leafref {
                    path "/rtp:rtp/rtp:routePolicys/rtp:routePolicy/rtp:name";
                  }
                  description
                    "When routes are imported from other routing protocols, the route-policy filter can be used to filter the routes and change route attributes.";
                  ext:allowDelete "true";
                }
                leaf medNew {
                  type uint64 {
                    range "0..4294967295";
                  }
                  description
                    "Specify the MED of imported routes.";
                  ext:allowDelete "true";
                }
                leaf nonRelayTnl {
                  when "../../../../../vrfName='_public_' and ../../../afType='ipv4uni'";
                  type boolean;
                  description
                    "Control whether imported route relay a tunnel.";
                }
              }
            }
            container networkRoutes {
              when "not(../afType='ipv4vpnmcast' or ../afType='mdt' or ../afType='vpntarget' or ../afType='vpnv4flow' or ../afType='vpnv6flow')";
              description
                "List of advertised routes.";
              list networkRoute {
                when "not(../../afType='rpd') or ../../afType!='ipv4vpn' and ../../afType!='ipv6vpn' and ../../afType!='ipv4flow' and ../../afType!='ipv6flow' and ../../afType!='l2vpnad' and ../../afType!='mvpn' and ../../afType!='mvpnv6' and ../../afType!='evpn' and ../../afType!='ipv4vpnmcast' and ../../afType!='mdt' and ../../afType!='ls' and ../../afType!='rpd' and ../../afType!='vpntarget'";
                key "networkAddress maskLen";
                description
                  "Configure the local routes that can be advertised by BGP. That is, add the routes in the local routing table to the BGP routing table in static mode and send them to the peer end. By default, BGP does not advertise any local route.";
                leaf networkAddress {
                  type inet:ip-address-no-zone;
                  description
                    "Specify the IP address advertised by BGP. An IPv4 address can be configured in the IPv4 address family, in dotted decimal notation, and an IPv6 routes can be configured in the IPv6 address family. Note: During the configuration of a network route, the IP address is adjusted based on the mask. It is recommended that you click Synchronize All after creating a network route.";
                }
                leaf maskLen {
                  type uint8 {
                    range "0..128";
                  }
                  description
                    "Specify the mask length of an IP address. The mask length ranges from 0 to 32 for an IPv4 address, and ranges from 0 to 128 for an IPv6 address.";
                }
                leaf networkPolicy {
                  type leafref {
                    path "/rtp:rtp/rtp:routePolicys/rtp:routePolicy/rtp:name";
                  }
                  description
                    "Specify the route-policy for route advertisement. The value is a string.";
                  ext:allowDelete "true";
                }
                leaf nonRelayTnl {
                  when "../../../../../vrfName='_public_' and ../../../afType='ipv4uni'";
                  type boolean;
                  description
                    "Control whether network route relay a tunnel.";
                }
              }
            }
            container aggregateRoutes {
              when "not(../afType='ipv4labeluni' or ../afType='ipv4vpnmcast' or ../afType='mdt' or ../afType='vpntarget' or ../afType='vpnv4flow' or ../afType='vpnv6flow')";
              description
                "List of summarized routes.";
              list aggregateRoute {
                when "not(../../afType='rpd') or ../../afType!='ipv4vpn' and ../../afType!='ipv6vpn' and ../../afType!='ipv4flow' and ../../afType!='ipv6flow' and ../../afType!='l2vpnad' and ../../afType!='mvpn' and ../../afType!='mvpnv6' and ../../afType!='evpn' and ../../afType!='ipv4vpnmcast' and ../../afType!='mdt' and ../../afType!='ls' and ../../afType!='rpd' and ../../afType!='vpntarget'";
                key "aggreAddress maskLength";
                description
                  "Create a summarized route in the BGP routing table. The local outbound interface of the summarized route is Null0. When another router receives the route, the route adds an outbound interface to the route. By default, route summarization is not performed. If the Origin attributes of the specific routes for the route summarization are different, the Origin attribute of the summarized route is that with the highest priority. Origin attributes are arranged in the priority order of  complete > egp > igp. A summarized route carries the community attribute of each specific route.";
                leaf aggreAddress {
                  type inet:ip-address-no-zone;
                  description
                    "Specify the IPv4 address or IPv6 address of a summarized route. Only IPv4 summarized routes can be configured in the IPv4 address family and only IPv6 summarized routes can be configured in the IPv6 address family.";
                }
                leaf maskLength {
                  type uint8 {
                    range "0..128";
                  }
                  description
                    "Specify the mask length of a summarized address. The mask length ranges from 0 to 32 for an IPv4 address, and ranges from 0 to 128 for an IPv6 address.";
                }
                leaf asSetEnable {
                  type boolean;
                  default "false";
                  description
                    "Generate routes with the AS-SET attribute. This option can be used to create a summarized route. The AS_Path attribute of the summarized route contains the AS-Path attributes of the specific routes for the route summarization. Exercise caution when using this option if multiple AS_Paths need to be summarized to prevent route flapping. ";
                }
                leaf detailSuppressed {
                  type boolean;
                  default "false";
                  description
                    "Suppress the advertisement of specific routes for the route summarization. Only the summarized route is advertised.";
                }
                leaf attributePolicy {
                  type leafref {
                    path "/rtp:rtp/rtp:routePolicys/rtp:routePolicy/rtp:name";
                  }
                  description
                    "Specify an attribute of summarized routes. If apply as-path is used to configure the AS_Path attribute that is used in the route Summarization policy, and the as-set keyword is set, the AS_Path attribute in the policy does not take effect.";
                  ext:allowDelete "true";
                }
                leaf originPolicy {
                  type leafref {
                    path "/rtp:rtp/rtp:routePolicys/rtp:routePolicy/rtp:name";
                  }
                  description
                    "Specify the name of a policy for generating summarized routes. Summarized routes are generated only when the routes match route-policy.";
                  ext:allowDelete "true";
                }
                leaf suppressPolicy {
                  type leafref {
                    path "/rtp:rtp/rtp:routePolicys/rtp:routePolicy/rtp:name";
                  }
                  description
                    "Specify a policy for suppressing the advertisement of specified routes. The routes matching the policy are not advertised, and other routes are advertised.";
                  ext:allowDelete "true";
                }
              }
            }
            container dampRoutes {
              when "not(../afType='ipv4vpnmcast' or ../afType='mdt' or ../afType='vpntarget' or ../afType='vpnv4flow' or ../afType='vpnv6flow')";
              description
                "List of route dampening.";
              list dampRoute {
                when "not(../../afType='rpd') or ../../afType!='ipv4vpn' and ../../afType!='ipv6vpn' and ../../afType!='ipv4flow' and ../../afType!='ipv6flow' and ../../afType!='l2vpnad' and ../../afType!='mvpn' and ../../afType!='mvpnv6' and ../../afType!='evpn' and ../../afType!='ipv4vpnmcast' and ../../afType!='mdt' and ../../afType!='ls' and ../../afType!='rpd' and ../../afType!='vpntarget'";
                key "peerType";
                description
                  "Enable BGP route dampening or modify various BGP route dampening parameters. By default, route dampening is not configured. If a suppression policy for route dampening is configured, routes are preferentially matched against the suppression parameters defined in the suppression policy. If no parameter is configured, the default value of each parameter is used. The four route dampening parameters are mutually dependent. If you configure one of the parameters, the other parameters also need to be configured. When you configure BGP route dampening, the values of reuse threshold, suppress threshold, and penalty ceiling must meet the inequality of reuse threshold < suppress threshold < penalty ceiling. If Maximum suppression time obtained by using the formula of Maximum suppression time = Half life (of reachable routes) x 60 x (ln(Penalty ceiling/Reuse threshold)/ln(2)) is smaller than 1, suppression cannot be performed. Ensure that the value of the maximum suppression time is equal to or greater than 1. This means that the value of the penalty ceiling/reuse threshold must be great enough.";
                leaf peerType {
                  type uint8 {
                    range "0..1";
                  }
                  must "not(../../../afType!='ipv4vpn') or (../../../afType!='ipv4vpn' and ../peerType=0)";
                  description
                    "Configure the peer type. The value of the penalty ceiling is an integer. The default value is 0(0:EBGP, 1:IBGP).";
                }
                leaf halfLifeReachTime {
                  type uint16 {
                    range "1..45";
                  }
                  default "15";
                  description
                    "Configure a half-life for reachable routes. The value is an integer, in minutes. The default value is 15.";
                }
                leaf reuse {
                  type uint16 {
                    range "1..20000";
                  }
                  default "750";
                  description
                    "Configure a threshold for a route to be unsuppressed. If the penalty value of the route falls below the threshold, the route is reused. The threshold value is an integer. The default value is 750.  ";
                }
                leaf suppress {
                  type uint16 {
                    range "1..20000";
                  }
                  default "2000";
                  description
                    "Configure a threshold for a route to be suppressed.  When the penalty value of the route exceeds the suppression threshold, the route is suppressed.  The configured suppression threshold must be greater than the reuse threshold. The value of the suppression threshold is an integer. The default value is 2000.";
                }
                leaf ceiling {
                  type uint16 {
                    range "1001..20000";
                  }
                  default "16000";
                  description
                    "Configure the penalty ceiling. The configured threshold must be greater than the suppression threshold. The value of the penalty ceiling is an integer. The default value is 16000.";
                }
                leaf dampPolicyName {
                  type leafref {
                    path "/rtp:rtp/rtp:routePolicys/rtp:routePolicy/rtp:name";
                  }
                  description
                    "Configure a suppression policy for route dampening. You can use a routing policy to select the routes to be suppressed.";
                  ext:allowDelete "true";
                }
                leaf updateStandard {
                  type boolean;
                  default "false";
                  description
                    "Update Standard.";
                }
              }
            }
            container filterPolicys {
              when "not(../afType='ipv4labeluni' or ../afType='ipv4vpnmcast' or ../afType='ls' or ../afType='mdt' or ../afType='vpntarget' or ../afType='vpnv4flow') or ../afType!='l2vpnad' and ../afType!='ipv4vpnmcast' and ../afType!='mdt' and ../afType!='ls' and ../afType!='rpd' and ../afType!='vpntarget'";
              description
                "List of filtering policies.";
              list filterPolicy {
                when "not(../../afType='evpn' or ../../afType='ipv4labeluni' or ../../afType='ipv4vpnmcast' or ../../afType='l2vpnad' or ../../afType='ls' or ../../afType='mdt' or ../../afType='mvpn' or ../../afType='mvpnv6' or ../../afType='rpd' or ../../afType='vpntarget' or ../../afType='vpnv4flow' or ../../afType='vpnv6flow') or ../../afType!='l2vpnad' and ../../afType!='ipv4vpnmcast' and ../../afType!='mdt' and ../../afType!='ls' and ../../afType!='rpd' and ../../afType!='vpntarget'";
                key "filterProtocol filterProcessId import export";
                description
                  "Specify a filtering policy. It is used to filter the routes received from a peer and the routes to be advertised to the peer. By default, routes are not filtered.";
                leaf filterProtocol {
                  type bgpcommFilterProtocol;
                  must "(../../../afType='ipv6uni' and (../filterProtocol='noprotocol' or ../filterProtocol='direct' or ../filterProtocol='isis' or ../filterProtocol='static' or ../filterProtocol='ospfv3' or ../filterProtocol='ripng' or ../filterProtocol='unr') ) or ((not(../../../afType='ipv6uni') and (../filterProtocol='noprotocol' or ../filterProtocol='direct' or ../filterProtocol='ospf' or ../filterProtocol='isis' or ../filterProtocol='static' or ../filterProtocol='rip' or ../filterProtocol='op-route') )) or ../../../afType!='ipv4vpn' and ../../../afType!='ipv6vpn' and ../import='false' or (not(../../../afType!='ipv4vpn' and ../../../afType!='ipv6vpn' and ../import='false') and ../filterProtocol='noprotocol') or not(../../../afType='ipv4vpn' or ../../../afType='ipv6vpn' or ../import='true')";
                  description
                    "Specify the name of a routing protocol. The routing protocol takes effect only on the routes to be advertised. The IPv4 address family supports the direct, IS-IS, OSPF, RIP, and static routing protocols. The IPv6 unicast address family of a public network instance supports the direct, IS-IS, OSPFv3, RIPng, and static routing protocols. The IPv6 address family of a VPNv6 instance supports the direct, IS-IS, RIPng, and static routing protocols.";
                }
                leaf filterProcessId {
                  type uint32 {
                    range "0..4294967295";
                  }
                  must "(../filterProtocol!='noprotocol' and ../filterProtocol!='direct' and ../filterProtocol!='static' and ../filterProtocol!='unr' and ../filterProtocol!='op-route' and ../filterProcessId!=0) or ((not(../filterProtocol!='noprotocol' and ../filterProtocol!='direct' and ../filterProtocol!='static' and ../filterProtocol!='unr' and ../filterProtocol!='op-route') and ../filterProcessId=0)) or not(../../../afType='ipv4vpn' or ../../../afType='ipv6vpn' or ../import='true')";
                  description
                    "Specify the process ID required to be matched. The value is an integer ranging from 1 to 65535. If direct or static routes need to be filtered, no process ID is required.";
                }
                leaf import {
                  type boolean;
				  must "(../import='false' and ../export='true') or (../import='true' and ../export='false')";
                  description
                    "Filter received routes. Only the routes that match the policy can be added to the BGP routing table. When a rule is configured for a named ACL, only the source address range specified by the source parameter and the time period specified by the time-range parameter take effect.";
                }
                leaf export {
                  type boolean;
                  must "(../import='false' and ../export='true') or (../import='true' and ../export='false')";
                  description
                    "Filter routes to be advertised. Only the routes that match the policy can be advertised by BGP. After the filtering function is configured, routes are filtered before being imported by BGP. Only the routes that match the policy can be added to the local BGP routing table and advertised by BGP. If a routing protocol is specified, only the routes of this protocol are filtered, and the routes of other protocols are not filtered. If no routing protocol is specified, all protocol routes are filtered. When a rule is configured for a named ACL, only the source address range specified by the source parameter and the time period specified by the time-range parameter take effect.";
                }
                leaf aclNameOrNum {
                  when "../../../afType!='ipv6uni' and ../../../afType!='ipv6vpn'";
                  type leafref {
                    path "/acl:acl/acl:aclGroups/acl:aclGroup/acl:aclNumOrName";
                  }
                  description
                    "Specify the name or number of an ACL Rule. The number value ranges from 2000 to 2999 and is used by basic ACL rules. The name must start with a letter, and the name is case-sensitive.";
                  ext:allowDelete "true";
                }
                leaf acl6NameOrNum {
                  when "not(../../../afType!='ipv6uni' and ../../../afType!='ipv6vpn')";
                  type acl6NumOrName;
                  description
                    "Specify the name or number of an ACL6 Rule. The number value ranges from 2000 to 2999 and is used by basic ACL6 rules. The name must start with a letter, and the name is case-sensitive.";
                  ext:allowDelete "true";
                }
                leaf preFlt4Name {
                  when "../../../afType!='ipv6uni' and ../../../afType!='ipv6vpn'";
                  type leafref {
                    path "/rtp:rtp/rtp:prefixFilters/rtp:prefixFilter/rtp:name";
                  }
                  description
                    "Specify the IPv4 prefix list name.";
                  ext:allowDelete "true";
                }
                leaf preFlt6Name {
                  when "not(../../../afType!='ipv6uni' and ../../../afType!='ipv6vpn')";
                  type ipPrefix;
                  description
                    "Specify the IPv6 prefix list name.";
                  ext:allowDelete "true";
                }
              }
            }
            container instanceImports {
              when "not(../afType='ipv4vpnmcast' or ../afType='mdt')";
              description
                "List of Instance Imported Routes.";
              list instanceImport {
                when "not(../../afType='rpd' or ../../afType='vpnv4flow' or ../../afType='vpnv6flow') or ../../afType!='ipv4vpn' and ../../afType!='ipv6vpn' and ../../afType!='ipv4flow' and ../../afType!='ipv6flow' and ../../afType!='l2vpnad' and ../../afType!='mvpn' and ../../afType!='mvpnv6' and ../../afType!='evpn' and ../../afType!='ipv4vpnmcast' and ../../afType!='ipv4multi' and ../../afType!='mdt' and ../../afType!='ls' and ../../afType!='rpd' and ../../afType!='vpntarget'";
                key "srcVrfName importRibSrcAddrFmType";
                description
                  "Instance Imported Route.";
                leaf srcVrfName {
                  type leafref {
                    path "/l3vpn:l3vpn/l3vpn:l3vpncomm/l3vpn:l3vpnInstances/l3vpn:l3vpnInstance/l3vpn:vrfName";
                  }
                  description
                    "Source VRF Name For Instance Imported Route.";
                }
                leaf importRibSrcAddrFmType {
                  type importRibType;
                  description
                    "Source Address Family Type For Instance Imported Route.";
                }
                leaf policyName {
                  type leafref {
                    path "/rtp:rtp/rtp:routePolicys/rtp:routePolicy/rtp:name";
                  }
                  description
                    "Policy for Route Import.";
                  ext:allowDelete "true";
                }
                leaf validRtEnable {
                  type boolean;
                  default "false";
                  description
                    "Imported Valid Route.";
                  ext:allowDelete "true";
                }
                leaf incLabelRt {
                  when "not(../../../afType!='ipv6uni' and ../../../afType!='ipv4uni' and ../../../afType!='ipv4labeluni' or ../importRibSrcAddrFmType='ipv4labeluni') or ../importRibSrcAddrFmType='ipv4uni'";
                  type boolean;
                  default "false";
                  description
                    "Imported Include Label Route.";
                  ext:allowDelete "true";
                }
              }
            }
            container routingTables {
              when "not(../afType='evpn')";
              config false;
              description
                "List of displayed route information in an address family.";
              list routingTable {
                when "../../afType!='ipv4flow' and ../../afType!='ipv6flow' and ../../afType!='l2vpnad' and ../../afType!='evpn' and ../../afType!='ls' and ../../afType!='rpd'";
                key "networkPrefix prefixMask routeTypeFlag imTableId rd from pathID";
                config false;
                description
                  "Information about routes.";
                leaf networkPrefix {
                  type inet:ip-address-no-zone;
                  config false;
                  description
                    "BGP route prefix.";
                }
                leaf prefixMask {
                  type uint8;
                  config false;
                  description
                    "Prefix mask.";
                }
                leaf routeTypeFlag {
                  type pub-type:bits32 {
                    ext:masklen 32;
                      ext:bit "ibgp" {
                        position 0;
                      }
                      ext:bit "ebgp" {
                        position 1;
                      }
                      ext:bit "network" {
                        position 2;
                      }
                      ext:bit "import" {
                        position 3;
                      }
                      ext:bit "auto-summary" {
                        position 4;
                      }
                      ext:bit "aggregate" {
                        position 5;
                      }
                      ext:bit "cpri" {
                        position 6;
                      }
                      ext:bit "pcri" {
                        position 7;
                      }
                      ext:bit "suppressed" {
                        position 8;
                      }
                      ext:bit "NHP-EMPTY" {
                        position 9;
                      }
                      ext:bit "NO-ADV" {
                        position 10;
                      }
                      ext:bit "local_cross" {
                        position 11;
                      }
                      ext:bit "remote_cross" {
                        position 12;
                      }
                      ext:bit "VD-BGP" {
                        position 13;
                      }
                      ext:bit "PATH_LOCAL" {
                        position 14;
                      }
                      ext:bit "PATH_GATEWAY" {
                        position 15;
                      }
                      ext:bit "policy_nopass" {
                        position 16;
                      }
                      ext:bit "supprenet" {
                        position 17;
                      }
                      ext:bit "dampened" {
                        position 18;
                      }
                      ext:bit "history" {
                        position 19;
                      }
                      ext:bit "select" {
                        position 20;
                      }
                      ext:bit "best" {
                        position 21;
                      }
                      ext:bit "backup" {
                        position 22;
                      }
                      ext:bit "attr_change" {
                        position 23;
                      }
                      ext:bit "NHLFE_CREATED" {
                        position 24;
                      }
                      ext:bit "ILM_CREATED" {
                        position 25;
                      }
                      ext:bit "NEXTHOP_CHANGE" {
                        position 26;
                      }
                      ext:bit "Invaild" {
                        position 27;
                      }
                      ext:bit "SOURCE_CHANGE" {
                        position 28;
                      }
                      ext:bit "IN_SELECTEDQ" {
                        position 29;
                      }
                      ext:bit "EXITIF_ERROR" {
                        position 30;
                      }
                      ext:bit "GROUP_HEAD" {
                        position 31;
                      }
                  }
                  config false;
                  description
                    "Route type.";
                }
                leaf imTableId {
                  type uint32 {
                    range "0..4294967295";
                  }
                  config false;
                  description
                    "ID of the routing table to which routes are imported.";
                }
                leaf rd {
                  type string {
                    length "1..22";
                  }
                  config false;
                  description
                    "Route distinguisher.";
                }
                leaf from {
                  type inet:ip-address-no-zone;
                  config false;
                  description
                    "Source peer that sends a route.";
                }
                leaf pathID {
                  type string {
                    length "1..50";
                  }
                  config false;
                  description
                    "Path ID.";
                }
                leaf remoteNextHopTunnelAddress {
                  type inet:ip-address-no-zone;
                  config false;
                  description
                    "The remote next hop tunnel address.";
                }
                leaf remoteNextHopMacAddress {
                  type pub-type:macAddress;
                  config false;
                  description
                    "The Remote next hop mac.";
                }
                leaf nexthop {
                  type inet:ip-address-no-zone;
                  config false;
                  description
                    "Next hop address to which packets are forwarded.";
                }
                leaf locPrf {
                  type uint32 {
                    range "0..4294967295";
                  }
                  config false;
                  description
                    "Local priority.The attribute is only fit for the routes from IBGP peer, not suit for which of EBGP peer.";
                }
                leaf prefVal {
                  type uint32 {
                    range "0..4294967295";
                  }
                  config false;
                  description
                    "Preferred value of a protocol.";
                }
                leaf prefrence {
                  type uint8 {
                    range "0..255";
                  }
                  config false;
                  description
                    "Priority of BGP routes.";
                }
                leaf pathAs {
                  type string {
                    length "1..300";
                  }
                  config false;
                  description
                    "List of the AS_Paths that packets pass through.";
                }
                leaf origin {
                  type bgpcommOrigin;
                  config false;
                  description
                    "Route origin.";
                }
                leaf med {
                  type uint32 {
                    range "0..4294967295";
                  }
                  config false;
                  description
                    "Route MED.The attribute is only fit for the routes from EBGP peer, not suit for which of IBGP peer.";
                }
                leaf flagString {
                  type string {
                    length "1..100";
                  }
                  config false;
                  description
                    "Route flag that contains a string of characters.";
                }
                leaf rtWorseReason {
                  type string {
                    length "1..50";
                  }
                  config false;
                  description
                    "Reason why a route is not selected.";
                }
                leaf peerString {
                  type string {
                    length "1..300";
                  }
                  config false;
                  description
                    "List of route sending peers.";
                }
                leaf time {
                  type uint32 {
                    range "0..4294967295";
                  }
                  config false;
                  description
                    "Time stamp of a route.";
                }
                leaf community {
                  type string {
                    length "1..120";
                  }
                  config false;
                  description
                    "Community attribute.";
                }
                leaf extCommunity {
                  type string {
                    length "1..300";
                  }
                  config false;
                  description
                    "Extended community attribute.";
                }
                leaf ifName {
                  type leafref {
                    path "/ifm:ifm/ifm:interfaces/ifm:interface/ifm:ifName";
                  }
                  config false;
                  description
                    "Name of the outbound interface of a route.";
                }
                leaf originator {
                  type inet:ip-address-no-zone;
                  config false;
                  description
                    "Router ID of the route initiator.";
                }
                leaf clusterList {
                  type string {
                    length "1..300";
                  }
                  config false;
                  description
                    "List of cluster IDs.";
                }
                leaf remoteRouteId {
                  type inet:ipv4-address-no-zone;
                  config false;
                  description
                    "Router ID of a peer.";
                }
                leaf relayNexthop {
                  type inet:ip-address-no-zone;
                  config false;
                  description
                    "Next hop to which a route is iterated.";
                }
                leaf relaytnlName {
                  type string {
                    length "1..64";
                  }
                  config false;
                  description
                    "Name of a tunnel to which a route is iterated.";
                }
                leaf isAtomicAggre {
                  type boolean;
                  default "false";
                  config false;
                  description
                    "Route carrying the atomic-aggregate attribute.";
                }
                leaf aggregatorAs {
                  type string {
                    length "1..11";
                  }
                  config false;
                  description
                    "AS number of the route summarizer.";
                }
                leaf aggregatorId {
                  type inet:ip-address-no-zone;
                  config false;
                  description
                    "ID of the route summarizer.";
                }
                leaf inLabel {
                  type uint32 {
                    range "0..4294967295";
                  }
                  config false;
                  description
                    "In-label.";
                }
                leaf outLabel {
                  type uint32 {
                    range "0..4294967295";
                  }
                  config false;
                  description
                    "Out-label.";
                }
                leaf disAttrString {
                  type string {
                    length "1..300";
                  }
                  config false;
                  description
                    "Discard the route attribute list.";
                }
                leaf vrfName {
                  type string {
                    length "1..31";
                  }
                  config false;
                  description
                    "Iterated Vrf .";
                }
                leaf remoteNextHopVni {
                  type uint32 {
                    range "0..4294967295";
                  }
                  config false;
                  description
                    "The remote next hop vni.";
                }
                leaf advNextHop {
                  type inet:ip-address-no-zone;
                  config false;
                  description
                    "Advertised Nexthop.";
                }
                leaf prefixSid {
                  type string {
                    length "1..60";
                  }
                  config false;
                  description
                    "PrefixSid attribute infomation of Route.";
                }
                leaf aigp {
                  type uint64;
                  config false;
                  description
                    "AIGP attribute information of Route.";
                }
                leaf attrSetString {
                  type string {
                    length "1..300";
                  }
                  config false;
                  description
                    "The attribute set information of Route.";
                }
              }
            }
            container lsNodeRoutes {
              when "not(../afType='evpn') or ../afType='ls'";
              config false;
              description
                "LS node route list.";
              list lsNodeRoute {
                when "not(../../afType='evpn')";
                key "routeType protocolType identifier lsNetwork nexthop from peerRID";
                config false;
                description
                  "LS node route.";
                leaf routeType {
                  type bgpcommLsRouteType;
                  config false;
                  description
                    "BGP-LS Route Type.";
                }
                leaf protocolType {
                  type bgpcommLsProtocolType;
                  config false;
                  description
                    "IGP Protocol type.";
                }
                leaf identifier {
                  type uint64 {
                    range "2..65535";
                  }
                  config false;
                  description
                    "Identifier of IGP protocol.";
                }
                leaf lsNetwork {
                  type string {
                    length "1..600";
                  }
                  config false;
                  description
                    "Prefix of BGP-LS route.";
                }
                leaf routeTypeFlag {
                  type pub-type:bits32;
                  config false;
                  description
                    "Route type.";
                  ext:masklen 32;
                    ext:bit "ibgp" {
                      position 0;
                    }
                    ext:bit "ebgp" {
                      position 1;
                    }
                    ext:bit "network" {
                      position 2;
                    }
                    ext:bit "import" {
                      position 3;
                    }
                    ext:bit "auto-summary" {
                      position 4;
                    }
                    ext:bit "aggregate" {
                      position 5;
                    }
                    ext:bit "cpri" {
                      position 6;
                    }
                    ext:bit "pcri" {
                      position 7;
                    }
                    ext:bit "suppressed" {
                      position 8;
                    }
                    ext:bit "NHP-EMPTY" {
                      position 9;
                    }
                    ext:bit "NO-ADV" {
                      position 10;
                    }
                    ext:bit "local_cross" {
                      position 11;
                    }
                    ext:bit "remote_cross" {
                      position 12;
                    }
                    ext:bit "VD-BGP" {
                      position 13;
                    }
                    ext:bit "PATH_LOCAL" {
                      position 14;
                    }
                    ext:bit "PATH_GATEWAY" {
                      position 15;
                    }
                    ext:bit "policy_nopass" {
                      position 16;
                    }
                    ext:bit "supprenet" {
                      position 17;
                    }
                    ext:bit "dampened" {
                      position 18;
                    }
                    ext:bit "history" {
                      position 19;
                    }
                    ext:bit "select" {
                      position 20;
                    }
                    ext:bit "best" {
                      position 21;
                    }
                    ext:bit "backup" {
                      position 22;
                    }
                    ext:bit "attr_change" {
                      position 23;
                    }
                    ext:bit "NHLFE_CREATED" {
                      position 24;
                    }
                    ext:bit "ILM_CREATED" {
                      position 25;
                    }
                    ext:bit "NEXTHOP_CHANGE" {
                      position 26;
                    }
                    ext:bit "Invaild" {
                      position 27;
                    }
                    ext:bit "SOURCE_CHANGE" {
                      position 28;
                    }
                    ext:bit "IN_SELECTEDQ" {
                      position 29;
                    }
                    ext:bit "EXITIF_ERROR" {
                      position 30;
                    }
                    ext:bit "GROUP_HEAD" {
                      position 31;
                    }
                }
                leaf nexthop {
                  type inet:ip-address-no-zone;
                  config false;
                  description
                    "Next hop address to which packets are forwarded.";
                }
                leaf flagString {
                  type string {
                    length "1..100";
                  }
                  config false;
                  description
                    "Route flag that contains a string of characters.";
                }
                leaf locPrf {
                  type uint32 {
                    range "0..4294967295";
                  }
                  config false;
                  description
                    "Local priority.";
                }
                leaf prefVal {
                  type uint32 {
                    range "0..4294967295";
                  }
                  config false;
                  description
                    "Preferred value of a protocol.";
                }
                leaf prefrence {
                  type uint8 {
                    range "0..255";
                  }
                  config false;
                  description
                    "Preference of a route.";
                }
                leaf pathAs {
                  type string {
                    length "1..300";
                  }
                  config false;
                  description
                    "List of the ASs that packets pass through.";
                }
                leaf med {
                  type uint32 {
                    range "0..4294967295";
                  }
                  config false;
                  description
                    "Route MED in the attribute node.";
                }
                leaf rtWorseReason {
                  type string {
                    length "1..50";
                  }
                  config false;
                  description
                    "Reason why a route is not selected.";
                }
                leaf time {
                  type uint32 {
                    range "0..4294967295";
                  }
                  config false;
                  description
                    "Time stamp of a route.";
                }
                leaf from {
                  type inet:ip-address-no-zone;
                  config false;
                  description
                    "Source peer that sends a route.";
                }
                leaf peerRID {
                  type inet:ip-address-no-zone;
                  config false;
                  description
                    "Router ID of source peer that sends a route.";
                }
                leaf ifName {
                  type pub-type:ifName;
                  config false;
                  description
                    "Name of the outbound interface of a route.";
                }
                leaf originator {
                  type inet:ip-address-no-zone;
                  config false;
                  description
                    "Router ID of the route initiator.";
                }
                leaf relayNexthop {
                  type inet:ip-address-no-zone;
                  config false;
                  description
                    "Next hop to which a route is iterated.";
                }
                leaf disAttrString {
                  type string {
                    length "1..300";
                  }
                  config false;
                  description
                    "Discard the route attribute list.";
                }
                leaf inLabel {
                  type uint32;
                  config false;
                  description
                    "In-label.";
                }
                leaf outLabel {
                  type uint32;
                  config false;
                  description
                    "Out-label.";
                }
                leaf mtIdVarAttrStr {
                  type string {
                    length "1..300";
                  }
                  config false;
                  description
                    "MT ID.";
                }
                leaf nodeName {
                  type string {
                    length "1..300";
                  }
                  config false;
                  description
                    "Name of IGP topology node.";
                }
                leaf isisAreaIdStr {
                  type string {
                    length "1..300";
                  }
                  config false;
                  description
                    "ISIS area ID.";
                }
                leaf sidLabelBinding {
                  type string {
                    length "1..300";
                  }
                  config false;
                  description
                    "SID/Label Binding.";
                }
                leaf srCapabilities {
                  type string {
                    length "1..300";
                  }
                  config false;
                  description
                    "Segment routing capabilities.";
                }
                leaf srAlgorithmStr {
                  type string {
                    length "1..300";
                  }
                  config false;
                  description
                    "Segment routing algorithm.";
                }
                leaf nodeFlagBits {
                  type pub-type:hexBinary;
                  config false;
                  description
                    "Node flags.";
                }
                leaf ipv4RouterIdOfLocalNode {
                  type string {
                    length "1..300";
                  }
                  config false;
                  description
                    "Ipv4 router id of local node.";
                }
                leaf ipv6RouterIdOfLocalNode {
                  type string {
                    length "1..300";
                  }
                  config false;
                  description
                    "Ipv6 router id of local node.";
                }
                leaf opaqueNodeProp {
                  type string {
                    length "1..300";
                  }
                  config false;
                  description
                    "Opaque node properties.";
                }
                leaf peerCount {
                  type uint32;
                  config false;
                  description
                    "Count of route sending peers.";
                }
                leaf advPeerListStr {
                  type string {
                    length "1..300";
                  }
                  config false;
                  description
                    "List of route sending peers.";
                }
              }
            }
            container lsLinkRoutes {
              when "../afType='ls'";
              config false;
              description
                "List of link routes.";
              list lsLinkRoute {
                key "routeType protocolType identifier lsNetwork nexthop from peerRID";
                config false;
                description
                  "Link route.";
                leaf routeType {
                  type bgpcommLsRouteType;
                  config false;
                  description
                    "BGP-LS Route Type.";
                }
                leaf protocolType {
                  type bgpcommLsProtocolType;
                  config false;
                  description
                    "IGP Protocol type.";
                }
                leaf identifier {
                  type uint64 {
                    range "2..65535";
                  }
                  config false;
                  description
                    "Identifier of IGP protocol.";
                }
                leaf lsNetwork {
                  type string {
                    length "1..600";
                  }
                  config false;
                  description
                    "Prefix of BGP-LS route.";
                }
                leaf routeTypeFlag {
                  type pub-type:bits32;
                  config false;
                  description
                    "Route type.";
                  ext:masklen 32;
                    ext:bit "ibgp" {
                      position 0;
                    }
                    ext:bit "ebgp" {
                      position 1;
                    }
                    ext:bit "network" {
                      position 2;
                    }
                    ext:bit "import" {
                      position 3;
                    }
                    ext:bit "auto-summary" {
                      position 4;
                    }
                    ext:bit "aggregate" {
                      position 5;
                    }
                    ext:bit "cpri" {
                      position 6;
                    }
                    ext:bit "pcri" {
                      position 7;
                    }
                    ext:bit "suppressed" {
                      position 8;
                    }
                    ext:bit "NHP-EMPTY" {
                      position 9;
                    }
                    ext:bit "NO-ADV" {
                      position 10;
                    }
                    ext:bit "local_cross" {
                      position 11;
                    }
                    ext:bit "remote_cross" {
                      position 12;
                    }
                    ext:bit "VD-BGP" {
                      position 13;
                    }
                    ext:bit "PATH_LOCAL" {
                      position 14;
                    }
                    ext:bit "PATH_GATEWAY" {
                      position 15;
                    }
                    ext:bit "policy_nopass" {
                      position 16;
                    }
                    ext:bit "supprenet" {
                      position 17;
                    }
                    ext:bit "dampened" {
                      position 18;
                    }
                    ext:bit "history" {
                      position 19;
                    }
                    ext:bit "select" {
                      position 20;
                    }
                    ext:bit "best" {
                      position 21;
                    }
                    ext:bit "backup" {
                      position 22;
                    }
                    ext:bit "attr_change" {
                      position 23;
                    }
                    ext:bit "NHLFE_CREATED" {
                      position 24;
                    }
                    ext:bit "ILM_CREATED" {
                      position 25;
                    }
                    ext:bit "NEXTHOP_CHANGE" {
                      position 26;
                    }
                    ext:bit "Invaild" {
                      position 27;
                    }
                    ext:bit "SOURCE_CHANGE" {
                      position 28;
                    }
                    ext:bit "IN_SELECTEDQ" {
                      position 29;
                    }
                    ext:bit "EXITIF_ERROR" {
                      position 30;
                    }
                    ext:bit "GROUP_HEAD" {
                      position 31;
                    }
                }
                leaf nexthop {
                  type inet:ip-address-no-zone;
                  config false;
                  description
                    "Next hop address to which packets are forwarded.";
                }
                leaf flagString {
                  type string {
                    length "1..100";
                  }
                  config false;
                  description
                    "Route flag that contains a string of characters.";
                }
                leaf locPrf {
                  type uint32 {
                    range "0..4294967295";
                  }
                  config false;
                  description
                    "Local priority.";
                }
                leaf prefVal {
                  type uint32 {
                    range "0..4294967295";
                  }
                  config false;
                  description
                    "Preferred value of a protocol.";
                }
                leaf prefrence {
                  type uint8 {
                    range "0..255";
                  }
                  config false;
                  description
                    "Preference of a route.";
                }
                leaf pathAs {
                  type string {
                    length "1..300";
                  }
                  config false;
                  description
                    "List of the ASs that packets pass through.";
                }
                leaf med {
                  type uint32 {
                    range "0..4294967295";
                  }
                  config false;
                  description
                    "Route MED in the attribute node.";
                }
                leaf rtWorseReason {
                  type string {
                    length "1..50";
                  }
                  config false;
                  description
                    "Reason why a route is not selected.";
                }
                leaf time {
                  type uint32 {
                    range "0..4294967295";
                  }
                  config false;
                  description
                    "Time stamp of a route.";
                }
                leaf from {
                  type inet:ip-address-no-zone;
                  config false;
                  description
                    "Source peer that sends a route.";
                }
                leaf peerRID {
                  type inet:ip-address-no-zone;
                  config false;
                  description
                    "Router ID of source peer that sends a route.";
                }
                leaf ifName {
                  type pub-type:ifName;
                  config false;
                  description
                    "Name of the outbound interface of a route.";
                }
                leaf originator {
                  type inet:ip-address-no-zone;
                  config false;
                  description
                    "Router ID of the route initiator.";
                }
                leaf relayNexthop {
                  type inet:ip-address-no-zone;
                  config false;
                  description
                    "Next hop to which a route is iterated.";
                }
                leaf disAttrString {
                  type string {
                    length "1..300";
                  }
                  config false;
                  description
                    "Discard the route attribute list.";
                }
                leaf inLabel {
                  type uint32;
                  config false;
                  description
                    "In-label.";
                }
                leaf outLabel {
                  type uint32;
                  config false;
                  description
                    "Out-label.";
                }
                leaf ipv4RouterIdOfLocalNode {
                  type string {
                    length "1..300";
                  }
                  config false;
                  description
                    "Ipv4 router id of local node.";
                }
                leaf ipv6RouterIdOfLocalNode {
                  type string {
                    length "1..300";
                  }
                  config false;
                  description
                    "Ipv6 router id of local node.";
                }
                leaf ipv4RouterIdOfRemoteNode {
                  type string {
                    length "1..300";
                  }
                  config false;
                  description
                    "Ipv4 router id of remote node.";
                }
                leaf ipv6RouterIdOfRemoteNode {
                  type string {
                    length "1..300";
                  }
                  config false;
                  description
                    "Ipv6 router id of remote node.";
                }
                leaf adminGroupColor {
                  type pub-type:hexBinary;
                  config false;
                  description
                    "adminGroupColor.";
                }
                leaf maxLinkBandWidth {
                  type uint32;
                  config false;
                  description
                    "Maximum Link Bandwidth(kbits/sec).";
                }
                leaf maxResvLinkBandWidth {
                  type uint32;
                  config false;
                  description
                    "Maximum Reservable Bandwidth(kbits/sec).";
                }
                leaf unResvBandWidth {
                  type string {
                    length "1..300";
                  }
                  config false;
                  description
                    "Maximum Unreserved Bandwidth(kbits/sec).";
                }
                leaf teDefaultMetric {
                  type uint32;
                  config false;
                  description
                    "teDefaultMetric.";
                }
                leaf linkProtectType {
                  type pub-type:bits16;
                  config false;
                  description
                    "Link Protect Type.";
                  ext:masklen 16;
                    ext:bit "null" {
                      position 0;
                    }
                    ext:bit "Extra Traffic" {
                      position 1;
                    }
                    ext:bit "Unprotected" {
                      position 2;
                    }
                    ext:bit "Shared" {
                      position 3;
                    }
                    ext:bit "Dedicated 1:1" {
                      position 4;
                    }
                    ext:bit "Dedicated 1+1" {
                      position 5;
                    }
                    ext:bit "Enhanced" {
                      position 6;
                    }
                    ext:bit "null7" {
                      position 7;
                    }
                    ext:bit "null8" {
                      position 8;
                    }
                    ext:bit "null9" {
                      position 9;
                    }
                    ext:bit "null10" {
                      position 10;
                    }
                    ext:bit "null11" {
                      position 11;
                    }
                    ext:bit "null12" {
                      position 12;
                    }
                    ext:bit "null13" {
                      position 13;
                    }
                    ext:bit "null14" {
                      position 14;
                    }
                    ext:bit "null15" {
                      position 15;
                    }
                }
                leaf mplsProtocolMask {
                  type pub-type:hexBinary;
                  config false;
                  description
                    "mplsProtocolMask.";
                }
                leaf igpMetric {
                  type uint32;
                  config false;
                  description
                    "igpMetric.";
                }
                leaf shareRiskLGStr {
                  type string {
                    length "1..300";
                  }
                  config false;
                  description
                    "shareRiskLGStr.";
                }
                leaf opaqueLinkProp {
                  type string {
                    length "1..300";
                  }
                  config false;
                  description
                    "Opaque link properties.";
                }
                leaf linkName {
                  type string {
                    length "1..300";
                  }
                  config false;
                  description
                    "Link name.";
                }
                leaf adjSegmentId {
                  type string {
                    length "1..300";
                  }
                  config false;
                  description
                    "adjSegmentId.";
                }
                leaf lanAdjSegmentId {
                  type string {
                    length "1..300";
                  }
                  config false;
                  description
                    "lanAdjSegmentId.";
                }
                leaf unresrvBwBc0 {
                  type string {
                    length "1..20";
                  }
                  config false;
                  description
                    "Unreserved Bandwidth.";
                }
                leaf bwConstraintModel {
                  type string {
                    length "1..20";
                  }
                  config false;
                  description
                    "Bandwidth Constraint Model.";
                }
                leaf bwConstraintBc0 {
                  type string {
                    length "1..20";
                  }
                  config false;
                  description
                    "Bandwidth Constraint.";
                }
                leaf loMultiBc0 {
                  type string {
                    length "1..10";
                  }
                  config false;
                  description
                    "Local Overbooking Multiplier.";
                }
                leaf bwConstModelStd {
                  type string {
                    length "1..20";
                  }
                  config false;
                  description
                    "Bandwidth Constraint Model(Standard).";
                }
                leaf bwConstBc0Std {
                  type string {
                    length "1..20";
                  }
                  config false;
                  description
                    "Bandwidth Constraint(Standard).";
                }
                leaf peerCount {
                  type uint32;
                  config false;
                  description
                    "Count of route sending peers.";
                }
                leaf advPeerListStr {
                  type string {
                    length "1..300";
                  }
                  config false;
                  description
                    "List of route sending peers.";
                }
              }
            }
            container lsPrefixRoutes {
              when "../afType='ls'";
              config false;
              description
                "List of prefix routes.";
              list lsPrefixRoute {
                key "routeType protocolType identifier lsNetwork nexthop from peerRID";
                config false;
                description
                  "Prefix route.";
                leaf routeType {
                  type bgpcommLsRouteType;
                  config false;
                  description
                    "BGP-LS Route Type.";
                }
                leaf protocolType {
                  type bgpcommLsProtocolType;
                  config false;
                  description
                    "IGP Protocol type.";
                }
                leaf identifier {
                  type uint64 {
                    range "2..65535";
                  }
                  config false;
                  description
                    "Identifier of IGP protocol.";
                }
                leaf lsNetwork {
                  type string {
                    length "1..600";
                  }
                  config false;
                  description
                    "Prefix of BGP-LS route.";
                }
                leaf routeTypeFlag {
                  type pub-type:bits32;
                  config false;
                  description
                    "Route type.";
                  ext:masklen 32;
                    ext:bit "ibgp" {
                      position 0;
                    }
                    ext:bit "ebgp" {
                      position 1;
                    }
                    ext:bit "network" {
                      position 2;
                    }
                    ext:bit "import" {
                      position 3;
                    }
                    ext:bit "auto-summary" {
                      position 4;
                    }
                    ext:bit "aggregate" {
                      position 5;
                    }
                    ext:bit "cpri" {
                      position 6;
                    }
                    ext:bit "pcri" {
                      position 7;
                    }
                    ext:bit "suppressed" {
                      position 8;
                    }
                    ext:bit "NHP-EMPTY" {
                      position 9;
                    }
                    ext:bit "NO-ADV" {
                      position 10;
                    }
                    ext:bit "local_cross" {
                      position 11;
                    }
                    ext:bit "remote_cross" {
                      position 12;
                    }
                    ext:bit "VD-BGP" {
                      position 13;
                    }
                    ext:bit "PATH_LOCAL" {
                      position 14;
                    }
                    ext:bit "PATH_GATEWAY" {
                      position 15;
                    }
                    ext:bit "policy_nopass" {
                      position 16;
                    }
                    ext:bit "supprenet" {
                      position 17;
                    }
                    ext:bit "dampened" {
                      position 18;
                    }
                    ext:bit "history" {
                      position 19;
                    }
                    ext:bit "select" {
                      position 20;
                    }
                    ext:bit "best" {
                      position 21;
                    }
                    ext:bit "backup" {
                      position 22;
                    }
                    ext:bit "attr_change" {
                      position 23;
                    }
                    ext:bit "NHLFE_CREATED" {
                      position 24;
                    }
                    ext:bit "ILM_CREATED" {
                      position 25;
                    }
                    ext:bit "NEXTHOP_CHANGE" {
                      position 26;
                    }
                    ext:bit "Invaild" {
                      position 27;
                    }
                    ext:bit "SOURCE_CHANGE" {
                      position 28;
                    }
                    ext:bit "IN_SELECTEDQ" {
                      position 29;
                    }
                    ext:bit "EXITIF_ERROR" {
                      position 30;
                    }
                    ext:bit "GROUP_HEAD" {
                      position 31;
                    }
                }
                leaf nexthop {
                  type inet:ip-address-no-zone;
                  config false;
                  description
                    "Next hop address to which packets are forwarded.";
                }
                leaf flagString {
                  type string {
                    length "1..100";
                  }
                  config false;
                  description
                    "Route flag that contains a string of characters.";
                }
                leaf locPrf {
                  type uint32 {
                    range "0..4294967295";
                  }
                  config false;
                  description
                    "Local priority.";
                }
                leaf prefVal {
                  type uint32 {
                    range "0..4294967295";
                  }
                  config false;
                  description
                    "Preferred value of a protocol.";
                }
                leaf prefrence {
                  type uint8 {
                    range "0..255";
                  }
                  config false;
                  description
                    "Preference of a route.";
                }
                leaf pathAs {
                  type string {
                    length "1..300";
                  }
                  config false;
                  description
                    "List of the ASs that packets pass through.";
                }
                leaf med {
                  type uint32 {
                    range "0..4294967295";
                  }
                  config false;
                  description
                    "Route MED in the attribute node.";
                }
                leaf rtWorseReason {
                  type string {
                    length "1..50";
                  }
                  config false;
                  description
                    "Reason why a route is not selected.";
                }
                leaf time {
                  type uint32 {
                    range "0..4294967295";
                  }
                  config false;
                  description
                    "Time stamp of a route.";
                }
                leaf from {
                  type inet:ip-address-no-zone;
                  config false;
                  description
                    "Source peer that sends a route.";
                }
                leaf peerRID {
                  type inet:ip-address-no-zone;
                  config false;
                  description
                    "Router ID of source peer that sends a route.";
                }
                leaf ifName {
                  type pub-type:ifName;
                  config false;
                  description
                    "Name of the outbound interface of a route.";
                }
                leaf originator {
                  type inet:ip-address-no-zone;
                  config false;
                  description
                    "Router ID of the route initiator.";
                }
                leaf relayNexthop {
                  type inet:ip-address-no-zone;
                  config false;
                  description
                    "Next hop to which a route is iterated.";
                }
                leaf disAttrString {
                  type string {
                    length "1..300";
                  }
                  config false;
                  description
                    "Discard the route attribute list.";
                }
                leaf inLabel {
                  type uint32;
                  config false;
                  description
                    "In-label.";
                }
                leaf outLabel {
                  type uint32;
                  config false;
                  description
                    "Out-label.";
                }
                leaf igpFlags {
                  type pub-type:hexBinary;
                  config false;
                  description
                    "IGP flags.";
                }
                leaf routeTags {
                  type string {
                    length "1..300";
                  }
                  config false;
                  description
                    "Route tag.";
                }
                leaf extRouteTag {
                  type string {
                    length "1..300";
                  }
                  config false;
                  description
                    "Extended route tag.";
                }
                leaf prefixMetric {
                  type uint32;
                  config false;
                  description
                    "prefixMetric.";
                }
                leaf ospfForwAddr {
                  type inet:ip-address-no-zone;
                  config false;
                  description
                    "ospfForwAddr.";
                }
                leaf opaquePrefixAtt {
                  type inet:ip-address-no-zone;
                  config false;
                  description
                    "Opaque prefix attribute.";
                }
                leaf prefixSID {
                  type string {
                    length "1..300";
                  }
                  config false;
                  description
                    "prefixSID.";
                }
                leaf peerCount {
                  type uint32;
                  config false;
                  description
                    "Count of route sending peers.";
                }
                leaf advPeerListStr {
                  type string {
                    length "1..300";
                  }
                  config false;
                  description
                    "List of route sending peers.";
                }
              }
            }
            container routingFlappingInfos {
              when "not(../afType='ipv4vpnmcast' or ../afType='mdt' or ../afType='vpntarget')";
              config false;
              description
                "Flapping statistics about BGP.";
              list routingFlappingInfo {
                when "not(../../afType='l2vpnad') or ../../afType!='l2vpnad' and ../../afType!='ipv4vpnmcast' and ../../afType!='mdt' and ../../afType!='ls' and ../../afType!='rpd' and ../../afType!='vpntarget'";
                key "networkAddress maskLength";
                config false;
                description
                  "Flapping statistics about BGP.";
                leaf networkAddress {
                  type inet:ip-address-no-zone;
                  config false;
                  description
                    "BGP route prefix.";
                }
                leaf maskLength {
                  type uint8 {
                    range "0..128";
                  }
                  config false;
                  description
                    "Mask length of an IP address.";
                }
                leaf fromPeer {
                  type inet:ip-address-no-zone;
                  config false;
                  description
                    "IP address of the peer that advertises routes.";
                }
                leaf origin {
                  type bgpcommOrigin;
                  config false;
                  description
                    "Route origin.";
                }
                leaf asPath {
                  type string {
                    length "1..10240";
                  }
                  config false;
                  description
                    "AS_Path attribute.";
                }
                leaf flaps {
                  type uint16 {
                    range "0..65535";
                  }
                  config false;
                  description
                    "Total number of route flapping times.";
                }
                leaf reuseTime {
                  type pub-type:timeTick;
                  config false;
                  description
                    "Reuse value.";
                }
                leaf durationTime {
                  type pub-type:timeTick;
                  config false;
                  description
                    "Duration that the flapping lasts.";
                }
              }
            }
            container routingDampenedInfos {
              when "not(../afType='ipv4vpnmcast' or ../afType='mdt' or ../afType='vpntarget')";
              config false;
              description
                "Statistics about dampened BGP routes.";
              list routingDampenedInfo {
                when "not(../../afType='l2vpnad') or ../../afType!='l2vpnad' and ../../afType!='ipv4vpnmcast' and ../../afType!='mdt' and ../../afType!='ls' and ../../afType!='rpd' and ../../afType!='vpntarget'";
                key "networkAddress maskLength";
                config false;
                description
                  "Statistics about a dampened BGP route.";
                leaf networkAddress {
                  type inet:ip-address-no-zone;
                  config false;
                  description
                    "BGP route prefix.";
                }
                leaf maskLength {
                  type uint8 {
                    range "0..128";
                  }
                  config false;
                  description
                    "Mask length of an IP address.";
                }
                leaf fromPeer {
                  type inet:ip-address-no-zone;
                  config false;
                  description
                    "IP address of the peer that advertises routes.";
                }
                leaf origin {
                  type bgpcommOrigin;
                  config false;
                  description
                    "Route origin.";
                }
                leaf asPath {
                  type string {
                    length "1..10240";
                  }
                  config false;
                  description
                    "AS_Path attribute.";
                }
                leaf reuseTime {
                  type pub-type:timeTick;
                  config false;
                  description
                    "Reuse value.";
                }
              }
            }
            container flowRoutingTables {
              when "not(../afType='ipv4vpnmcast' or ../afType='mdt' or ../afType='vpntarget')";
              config false;
              description
                "List of displayed BGP Flow Specification route information.";
              list flowRoutingTable {
                when "not(../../afType!='ipv4flow' and ../../afType!='ipv6flow' and ../../afType!='vpnv4flow' and ../../afType!='vpnv6flow')";
                key "reIndex isLocalRoute localRouteName from";
                config false;
                description
                  "Information about BGP Flow Specification routes.";
                leaf reIndex {
                  type uint32 {
                    range "1..4294967295";
                  }
                  config false;
                  description
                    "BGP Flow Specification route index. The value is an integer ranging from 1 to 4294967295.";
                }
                leaf isLocalRoute {
                  type boolean;
                  config false;
                  description
                    "The BGP Flow Specification route is a local route.";
                }
                leaf localRouteName {
                  type string {
                    length "1..30";
                  }
                  config false;
                  description
                    "Name of a local BGP Flow Specification route.";
                }
                leaf from {
                  type inet:ip-address-no-zone;
                  config false;
                  description
                    "Source peer that sends a route.";
                }
                leaf routeTypeFlag {
                  type pub-type:bits32;
                  config false;
                  description
                    "Route Type.";
                  ext:masklen 32;
                    ext:bit "ibgp" {
                      position 0;
                    }
                    ext:bit "ebgp" {
                      position 1;
                    }
                    ext:bit "network" {
                      position 2;
                    }
                    ext:bit "import" {
                      position 3;
                    }
                    ext:bit "auto-summary" {
                      position 4;
                    }
                    ext:bit "aggregate" {
                      position 5;
                    }
                    ext:bit "cpri" {
                      position 6;
                    }
                    ext:bit "pcri" {
                      position 7;
                    }
                    ext:bit "suppressed" {
                      position 8;
                    }
                    ext:bit "NHP-EMPTY" {
                      position 9;
                    }
                    ext:bit "NO-ADV" {
                      position 10;
                    }
                    ext:bit "local_cross" {
                      position 11;
                    }
                    ext:bit "remote_cross" {
                      position 12;
                    }
                    ext:bit "VD-BGP" {
                      position 13;
                    }
                    ext:bit "PATH_LOCAL" {
                      position 14;
                    }
                    ext:bit "PATH_GATEWAY" {
                      position 15;
                    }
                    ext:bit "policy_nopass" {
                      position 16;
                    }
                    ext:bit "supprenet" {
                      position 17;
                    }
                    ext:bit "dampened" {
                      position 18;
                    }
                    ext:bit "history" {
                      position 19;
                    }
                    ext:bit "select" {
                      position 20;
                    }
                    ext:bit "best" {
                      position 21;
                    }
                    ext:bit "backup" {
                      position 22;
                    }
                    ext:bit "attr_change" {
                      position 23;
                    }
                    ext:bit "NHLFE_CREATED" {
                      position 24;
                    }
                    ext:bit "ILM_CREATED" {
                      position 25;
                    }
                    ext:bit "NEXTHOP_CHANGE" {
                      position 26;
                    }
                    ext:bit "Invaild" {
                      position 27;
                    }
                    ext:bit "SOURCE_CHANGE" {
                      position 28;
                    }
                    ext:bit "IN_SELECTEDQ" {
                      position 29;
                    }
                    ext:bit "EXITIF_ERROR" {
                      position 30;
                    }
                    ext:bit "GROUP_HEAD" {
                      position 31;
                    }
                }
                leaf peerRouterId {
                  type inet:ipv4-address-no-zone;
                  config false;
                  description
                    "Router ID of a peer.";
                }
                leaf order {
                  type uint32 {
                    range "0..4294967295";
                  }
                  config false;
                  description
                    "Filtering rule delivery order.";
                }
                leaf isApplyDeny {
                  type boolean;
                  config false;
                  description
                    "Deny the traffic that matches the traffic policy.";
                }
                leaf isApplySample {
                  type boolean;
                  config false;
                  description
                    "Enable Apply Sample.";
                }
                leaf isApplyNextTerm {
                  type boolean;
                  config false;
                  description
                    "Enable Apply Next-Term.";
                }
                leaf remarkDscp {
                  type string {
                    length "1..50";
                  }
                  config false;
                  description
                    "Filtering rules to re-mark the DSCP value.";
                }
                leaf trafficRate {
                  type string {
                    length "1..50";
                  }
                  config false;
                  description
                    "Traffic rate rule.";
                }
                leaf redirectIP {
                  type string {
                    length "9..17";
                  }
                  config false;
                  description
                    "Redirect IP of a BGP Flow Specification route.";
                }
                leaf relayTnlName {
                  type string {
                    length "1..64";
                  }
                  config false;
                  description
                    "Flow Route Redirect Relay Tunnel";
                }
                leaf validationResult {
                  type pub-type:bits8;
                  config false;
                  description
                    "EBGP Redirect IP Validate Result";
                  ext:masklen 7;
                    ext:bit "notenable" {
                      position 0;
                    }
                    ext:bit "checking" {
                      position 1;
                    }
                    ext:bit "accept" {
                      position 2;
                    }
                    ext:bit "discard" {
                      position 3;
                    }
                }
                leaf vpnTarget {
                  type string {
                    length "1..22";
                  }
                  config false;
                  description
                    "VPN target of a BGP Flow Specification route.";
                }
                leaf isReflectClient {
                  type boolean;
                  config false;
                  description
                    "The device is an RR.";
                }
                leaf dscp {
                  type string {
                    length "1..50";
                  }
                  config false;
                  description
                    "DSCP rule.";
                }
                leaf destinationPrefix {
                  type inet:ip-address-no-zone;
                  config false;
                  description
                    "Destination prefix-based filtering rule.";
                }
                leaf desPrefixMaskLen {
                  type uint8 {
                    range "0..128";
                  }
                  config false;
                  description
                    "Destination prefix mask length.";
                }
                leaf sourcePrefix {
                  type inet:ip-address-no-zone;
                  config false;
                  description
                    "Source prefix-based filtering rule.";
                }
                leaf srcPrefixMaskLen {
                  type uint8 {
                    range "0..128";
                  }
                  config false;
                  description
                    "Source Prefix mask length.";
                }
                leaf protocol {
                  type string {
                    length "1..50";
                  }
                  config false;
                  description
                    "IP protocol-based filtering rule for BGP Flow Specification routes.";
                }
                leaf port {
                  type string {
                    length "1..50";
                  }
                  config false;
                  description
                    "Port number-based filtering rule.";
                }
                leaf destinationPort {
                  type string {
                    length "1..50";
                  }
                  config false;
                  description
                    "Destination port number-based filtering rule.";
                }
                leaf sourcePort {
                  type string {
                    length "1..50";
                  }
                  config false;
                  description
                    "Source port number-based filtering rule.";
                }
                leaf icmpType {
                  type string {
                    length "1..50";
                  }
                  config false;
                  description
                    "ICMP type-based filtering rule.";
                }
                leaf icmpCode {
                  type string {
                    length "1..50";
                  }
                  config false;
                  description
                    "ICMP code-based filtering rule.";
                }
                leaf tcpFlags {
                  type string {
                    length "1..50";
                  }
                  config false;
                  description
                    "TCP Flag-based filtering rule.";
                }
                leaf packetlength {
                  type string {
                    length "1..50";
                  }
                  config false;
                  description
                    "Packet length-based filtering rule.";
                }
                leaf fragmentType {
                  type string {
                    length "1..50";
                  }
                  config false;
                  description
                    "Fragment type-based filtering rule.";
                }
                leaf isUnkownRule {
                  type boolean;
                  config false;
                  description
                    "Unknown rule.";
                }
                leaf med {
                  type uint32 {
                    range "0..4294967295";
                  }
                  config false;
                  description
                    "MED.";
                }
                leaf prefVal {
                  type uint32 {
                    range "0..4294967295";
                  }
                  config false;
                  description
                    "PrefVal.";
                }
                leaf localPrefrence {
                  type uint8 {
                    range "0..255";
                  }
                  config false;
                  description
                    "Local-Preference.";
                }
                leaf origin {
                  type bgpcommOrigin;
                  config false;
                  description
                    "Route origin.";
                }
                leaf originator {
                  type inet:ipv4-address-no-zone;
                  config false;
                  description
                    "Router ID of the route initiator.";
                }
                leaf routeDuration {
                  type uint32 {
                    range "0..4294967295";
                  }
                  config false;
                  description
                    "Route duration.";
                }
                leaf flagString {
                  type string {
                    length "1..100";
                  }
                  config false;
                  description
                    "Route flag that contains a string of characters.";
                }
                leaf community {
                  type string {
                    length "1..120";
                  }
                  config false;
                  description
                    "Community attribute of a BGP Flow Specification route.";
                }
                leaf extCommunity {
                  type string {
                    length "1..300";
                  }
                  config false;
                  description
                    "Extended community attribute of a BGP Flow Specification route.";
                }
                leaf clusterlist {
                  type string {
                    length "1..300";
                  }
                  config false;
                  description
                    "Cluster list of a BGP Flow Specification route.";
                }
                leaf pathAs {
                  type string {
                    length "1..300";
                  }
                  config false;
                  description
                    "List of the AS_Paths that packets pass through.";
                }
                leaf rtWorseReason {
                  type string {
                    length "1..50";
                  }
                  config false;
                  description
                    "Reason why a route is not selected.";
                }
                leaf peerString {
                  type string {
                    length "1..300";
                  }
                  config false;
                  description
                    "List of route sending peers.";
                }
                leaf ruleNumber {
                  type uint64;
                  config false;
                  description
                    "Number of rules for BGP Flow Specification routes.";
                }
                leaf matchPackets {
                  type uint64;
                  config false;
                  description
                    "Number of matched packets.";
                }
                leaf matchBytes {
                  type uint64;
                  config false;
                  description
                    "Number of matched bytes.";
                }
                leaf matchPacketPer30Sec {
                  type uint64;
                  config false;
                  description
                    "Number of matched packets each 30 seconds.";
                }
                leaf matchBytePer30Sec {
                  type uint64;
                  config false;
                  description
                    "Number of matched bytes each 30 seconds.";
                }
                leaf trafActFlag {
                  type pub-type:bits8;
                  config false;
                  description
                    "Traffic action flag.";
                  ext:masklen 7;
                    ext:bit "route-policy-distribute" {
                      position 1;
                    }
                }
                leaf invalidReason {
                  type string {
                    length "0..250";
                  }
                  config false;
                  description
                    "Why a route cannot be delivered to the FIB.";
                }
                container wideCommunitys {
                  config false;
                  description
                    "Wide-community information.";
                  list wideCommunity {
                    key "index type flag hopCount";
                    config false;
                    description
                      "Wide-community information.";
                    leaf index {
                      type uint32;
                      config false;
                      description
                        "Index.";
                    }
                    leaf type {
                      type uint32;
                      config false;
                      description
                        "Type.";
                    }
                    leaf flag {
                      type pub-type:hexBinary;
                      config false;
                      description
                        "Flag.";
                    }
                    leaf hopCount {
                      type uint32;
                      config false;
                      description
                        "Hop count.";
                    }
                    leaf communityValue {
                      type pub-type:hexBinary;
                      config false;
                      description
                        "Community value.";
                    }
                    leaf sourceAs {
                      type asNumberValidate;
                      config false;
                      description
                        "Source AS.";
                    }
                    leaf contextAs {
                      type asNumberValidate;
                      config false;
                      description
                        "Context AS.";
                    }
                    leaf param {
                      type string {
                        length "0..2030";
                      }
                      config false;
                      description
                        "Parameter.";
                    }
                  }
                }
                container redirectIpRelays {
                  config false;
                  description
                    "Redirection IP information.";
                  list redirectIpRelay {
                    key "redirectIp";
                    config false;
                    description
                      "Redirection IP information.";
                    leaf redirectIp {
                      type inet:ipv4-address-no-zone;
                      config false;
                      description
                        "Redirection IP address.";
                    }
                    leaf redirectOpt {
                      type uint32;
                      config false;
                      description
                        "Operation code.";
                    }
                    leaf redirectResult {
                      type string {
                        length "1..100";
                      }
                      config false;
                      description
                        "Iteration result.";
                    }
                    leaf relayNextHop {
                      type inet:ipv4-address-no-zone;
                      config false;
                      description
                        "IP iteration next hop.";
                    }
                    leaf outIfName {
                      type pub-type:ifName;
                      config false;
                      description
                        "IP iteration outbound interface.";
                    }
                    leaf relayTnlNextHop {
                      type inet:ipv4-address-no-zone;
                      config false;
                      description
                        "Tunnel iteration next hop.";
                    }
                    leaf relayTnlOutIfName {
                      type pub-type:ifName;
                      config false;
                      description
                        "Tunnel iteration outbund interface.";
                    }
                  }
                }
                container flowInfGrpStats {
                  config false;
                  description
                    "Statistics of the BGP Flow Specification route with the specified reIndex and flow interface group ID.";
                  list flowInfGrpStat {
                    key "flowIfGrpIndex";
                    config false;
                    description
                      "Statistic of the BGP Flow Specification route with the specified reIndex and flow interface group ID.";
                    leaf flowIfGrpIndex {
                      type uint32 {
                        range "0..16383";
                      }
                      config false;
                      description
                        "Flow interface group ID.";
                    }
                    leaf ruleNumber {
                      type uint64;
                      config false;
                      description
                        "Number of rules for BGP Flow Specification routes.";
                    }
                    leaf matchPackets {
                      type uint64;
                      config false;
                      description
                        "Number of matched packets.";
                    }
                    leaf matchBytes {
                      type uint64;
                      config false;
                      description
                        "Number of matched bytes.";
                    }
                    leaf matchPacketPer30Sec {
                      type uint64;
                      config false;
                      description
                        "Number of matched packets each 30 seconds.";
                    }
                    leaf matchBytePer30Sec {
                      type uint64;
                      config false;
                      description
                        "Number of matched bytes each 30 seconds.";
                    }
                  }
                }
              }
            }
            container l2vpnAdRoutingTables {
              when "not(../afType='ipv4vpnmcast' or ../afType='mdt' or ../afType='vpntarget')";
              config false;
              description
                "List of displayed BGP L2VPN-AD route information.";
              list l2vpnAdRoutingTable {
                when "not(../../afType='rpd' or ../../afType='vpnv4flow') or ../../afType='l2vpnad'";
                key "l2vpnAdNlri rd from routeTypeFlag imTableId";
                config false;
                description
                  "Information about BGP L2VPN-AD routes.";
                leaf l2vpnAdNlri {
                  type inet:ipv4-address-no-zone;
                  config false;
                  description
                    "Prefix of a BGP route.";
                }
                leaf rd {
                  type string {
                    length "1..22";
                  }
                  config false;
                  description
                    "Route distinguisher.";
                }
                leaf from {
                  type inet:ip-address-no-zone;
                  config false;
                  description
                    "Source peer that sends a route.";
                }
                leaf routeTypeFlag {
                  type pub-type:bits32 {
                    ext:masklen 32;
                      ext:bit "ibgp" {
                        position 0;
                      }
                      ext:bit "ebgp" {
                        position 1;
                      }
                      ext:bit "network" {
                        position 2;
                      }
                      ext:bit "import" {
                        position 3;
                      }
                      ext:bit "auto-summary" {
                        position 4;
                      }
                      ext:bit "aggregate" {
                        position 5;
                      }
                      ext:bit "cpri" {
                        position 6;
                      }
                      ext:bit "pcri" {
                        position 7;
                      }
                      ext:bit "suppressed" {
                        position 8;
                      }
                      ext:bit "NHP-EMPTY" {
                        position 9;
                      }
                      ext:bit "NO-ADV" {
                        position 10;
                      }
                      ext:bit "local_cross" {
                        position 11;
                      }
                      ext:bit "remote_cross" {
                        position 12;
                      }
                      ext:bit "VD-BGP" {
                        position 13;
                      }
                      ext:bit "PATH_LOCAL" {
                        position 14;
                      }
                      ext:bit "PATH_GATEWAY" {
                        position 15;
                      }
                      ext:bit "policy_nopass" {
                        position 16;
                      }
                      ext:bit "supprenet" {
                        position 17;
                      }
                      ext:bit "dampened" {
                        position 18;
                      }
                      ext:bit "history" {
                        position 19;
                      }
                      ext:bit "select" {
                        position 20;
                      }
                      ext:bit "best" {
                        position 21;
                      }
                      ext:bit "backup" {
                        position 22;
                      }
                      ext:bit "attr_change" {
                        position 23;
                      }
                      ext:bit "NHLFE_CREATED" {
                        position 24;
                      }
                      ext:bit "ILM_CREATED" {
                        position 25;
                      }
                      ext:bit "NEXTHOP_CHANGE" {
                        position 26;
                      }
                      ext:bit "Invaild" {
                        position 27;
                      }
                      ext:bit "SOURCE_CHANGE" {
                        position 28;
                      }
                      ext:bit "IN_SELECTEDQ" {
                        position 29;
                      }
                      ext:bit "EXITIF_ERROR" {
                        position 30;
                      }
                      ext:bit "GROUP_HEAD" {
                        position 31;
                      }
                  }
                  config false;
                  description
                    "Route type.";
                }
                leaf imTableId {
                  type uint32 {
                    range "0..4294967295";
                  }
                  config false;
                  description
                    "ID of the routing table to which routes are imported.";
                }
                leaf nexthop {
                  type inet:ip-address-no-zone;
                  config false;
                  description
                    "Next hop address to which packets are forwarded.";
                }
                leaf locPrf {
                  type uint32 {
                    range "0..4294967295";
                  }
                  config false;
                  description
                    "Local priority.The attribute is only fit for the routes from IBGP peer, not suit for which of EBGP peer.";
                }
                leaf prefVal {
                  type uint32 {
                    range "0..4294967295";
                  }
                  config false;
                  description
                    "Preferred value of a protocol.";
                }
                leaf prefrence {
                  type uint8 {
                    range "0..255";
                  }
                  config false;
                  description
                    "Priority of BGP routes.";
                }
                leaf pathAs {
                  type string {
                    length "1..300";
                  }
                  config false;
                  description
                    "List of the AS_Paths that packets pass through.";
                }
                leaf origin {
                  type bgpcommOrigin;
                  config false;
                  description
                    "Route origin.";
                }
                leaf med {
                  type uint32 {
                    range "0..4294967295";
                  }
                  config false;
                  description
                    "Route MED.The attribute is only fit for the routes from EBGP peer, not suit for which of IBGP peer.";
                }
                leaf flagString {
                  type string {
                    length "1..100";
                  }
                  config false;
                  description
                    "Route flag that contains a string of characters.";
                }
                leaf rtWorseReason {
                  type string {
                    length "1..50";
                  }
                  config false;
                  description
                    "Reason why a route is not selected.";
                }
                leaf peerString {
                  type string {
                    length "1..300";
                  }
                  config false;
                  description
                    "List of route sending peers.";
                }
                leaf time {
                  type uint32 {
                    range "0..4294967295";
                  }
                  config false;
                  description
                    "Time stamp of a route.";
                }
                leaf community {
                  type string {
                    length "1..120";
                  }
                  config false;
                  description
                    "Community attribute.";
                }
                leaf extCommunity {
                  type string {
                    length "1..300";
                  }
                  config false;
                  description
                    "Extended community attribute.";
                }
                leaf ifName {
                  type pub-type:ifName;
                  config false;
                  description
                    "Name of the outbound interface of a route.";
                }
                leaf originator {
                  type inet:ip-address-no-zone;
                  config false;
                  description
                    "Router ID of the route initiator.";
                }
                leaf clusterList {
                  type string {
                    length "1..300";
                  }
                  config false;
                  description
                    "List of cluster IDs.";
                }
                leaf remoteRouteId {
                  type inet:ipv4-address-no-zone;
                  config false;
                  description
                    "Router ID of a peer.";
                }
                leaf relayNexthop {
                  type inet:ip-address-no-zone;
                  config false;
                  description
                    "Next hop to which a route is iterated.";
                }
                leaf relaytnlName {
                  type string {
                    length "1..64";
                  }
                  config false;
                  description
                    "Name of a tunnel to which a route is iterated.";
                }
                leaf inLabel {
                  type uint32 {
                    range "0..4294967295";
                  }
                  config false;
                  description
                    "In-label.";
                }
                leaf outLabel {
                  type uint32 {
                    range "0..4294967295";
                  }
                  config false;
                  description
                    "Out-label.";
                }
                leaf pmsiString {
                  type string {
                    length "1..300";
                  }
                  config false;
                  description
                    "PMSI attribute.";
                }
                leaf advNextHop {
                  type inet:ip-address-no-zone;
                  config false;
                  description
                    "Next hop of an BGP.";
                }
              }
            }
            container ngRoutingTable1s {
              when "not(../afType='ipv4vpnmcast' or ../afType='mdt' or ../afType='vpntarget' or ../afType='vpnv4flow' or ../afType='vpnv6flow')";
              config false;
              description
                "List of displayed BGP Ng route type 1 information.";
              list ngRoutingTable1 {
                when "not(../../afType!='mvpn' and ../../afType!='mvpnv6' or ../../afType='rpd')";
                key "ngNlri rd from ngRouteType routeTypeFlag";
                config false;
                description
                  "Information about BGP Ng routes type 1.";
                leaf ngNlri {
                  type inet:ipv4-address-no-zone;
                  config false;
                  description
                    "Prefix of a BGP route.";
                }
                leaf imTableId {
                  type uint32 {
                    range "0..4294967295";
                  }
                  config false;
                  description
                    "ID of the routing table to which routes are imported.";
                }
                leaf nexthop {
                  type inet:ip-address-no-zone;
                  config false;
                  description
                    "Next hop address to which packets are forwarded.";
                }
                leaf locPrf {
                  type uint32 {
                    range "0..4294967295";
                  }
                  config false;
                  description
                    "Local-preference.";
                }
                leaf prefVal {
                  type uint32 {
                    range "0..4294967295";
                  }
                  config false;
                  description
                    "Preferred value of a protocol.";
                }
                leaf prefrence {
                  type uint8 {
                    range "0..255";
                  }
                  config false;
                  description
                    "Priority of BGP routes.";
                }
                leaf pathAs {
                  type string {
                    length "1..300";
                  }
                  config false;
                  description
                    "List of the AS_Paths that packets pass through.";
                }
                leaf origin {
                  type bgpcommOrigin;
                  config false;
                  description
                    "Route origin.";
                }
                leaf med {
                  type uint32 {
                    range "0..4294967295";
                  }
                  config false;
                  description
                    "Route MED.";
                }
                leaf flagString {
                  type string {
                    length "1..100";
                  }
                  config false;
                  description
                    "Route flag that contains a string of characters.";
                }
                leaf rd {
                  type string {
                    length "1..22";
                  }
                  config false;
                  description
                    "Route distinguisher.";
                }
                leaf rtWorseReason {
                  type string {
                    length "1..50";
                  }
                  config false;
                  description
                    "Reason why a route is not selected.";
                }
                leaf peerString {
                  type string {
                    length "1..300";
                  }
                  config false;
                  description
                    "List of route sending peers.";
                }
                leaf time {
                  type uint32 {
                    range "0..4294967295";
                  }
                  config false;
                  description
                    "Time stamp of a route.";
                }
                leaf community {
                  type string {
                    length "1..120";
                  }
                  config false;
                  description
                    "Community attribute.";
                }
                leaf extCommunity {
                  type string {
                    length "1..300";
                  }
                  config false;
                  description
                    "Extended community attribute.";
                }
                leaf from {
                  type inet:ip-address-no-zone;
                  config false;
                  description
                    "Source peer that sends a route.";
                }
                leaf ifName {
                  type pub-type:ifName;
                  config false;
                  description
                    "Name of the outbound interface of a route.";
                }
                leaf originator {
                  type inet:ip-address-no-zone;
                  config false;
                  description
                    "Router ID of the route initiator.";
                }
                leaf clusterList {
                  type string {
                    length "1..300";
                  }
                  config false;
                  description
                    "List of cluster IDs.";
                }
                leaf remoteRouteId {
                  type inet:ipv4-address-no-zone;
                  config false;
                  description
                    "Router ID of a peer.";
                }
                leaf relayNexthop {
                  type inet:ip-address-no-zone;
                  config false;
                  description
                    "Next hop to which a route is iterated.";
                }
                leaf relaytnlName {
                  type string {
                    length "1..64";
                  }
                  config false;
                  description
                    "Name of a tunnel to which a route is iterated.";
                }
                leaf inLabel {
                  type uint32 {
                    range "0..4294967295";
                  }
                  config false;
                  description
                    "In-label.";
                }
                leaf outLabel {
                  type uint32 {
                    range "0..4294967295";
                  }
                  config false;
                  description
                    "Out-label.";
                }
                leaf ngRouteType {
                  type string {
                    length "1..50";
                  }
                  config false;
                  description
                    "Route type.";
                }
                leaf routeTypeFlag {
                  type pub-type:bits32;
                  config false;
                  description
                    "Route type.";
                  ext:masklen 32;
                    ext:bit "ibgp" {
                      position 0;
                    }
                    ext:bit "ebgp" {
                      position 1;
                    }
                    ext:bit "network" {
                      position 2;
                    }
                    ext:bit "import" {
                      position 3;
                    }
                    ext:bit "auto-summary" {
                      position 4;
                    }
                    ext:bit "aggregate" {
                      position 5;
                    }
                    ext:bit "cpri" {
                      position 6;
                    }
                    ext:bit "pcri" {
                      position 7;
                    }
                    ext:bit "suppressed" {
                      position 8;
                    }
                    ext:bit "NHP-EMPTY" {
                      position 9;
                    }
                    ext:bit "NO-ADV" {
                      position 10;
                    }
                    ext:bit "local_cross" {
                      position 11;
                    }
                    ext:bit "remote_cross" {
                      position 12;
                    }
                    ext:bit "VD-BGP" {
                      position 13;
                    }
                    ext:bit "PATH_LOCAL" {
                      position 14;
                    }
                    ext:bit "PATH_GATEWAY" {
                      position 15;
                    }
                    ext:bit "policy_nopass" {
                      position 16;
                    }
                    ext:bit "supprenet" {
                      position 17;
                    }
                    ext:bit "dampened" {
                      position 18;
                    }
                    ext:bit "history" {
                      position 19;
                    }
                    ext:bit "select" {
                      position 20;
                    }
                    ext:bit "best" {
                      position 21;
                    }
                    ext:bit "backup" {
                      position 22;
                    }
                    ext:bit "attr_change" {
                      position 23;
                    }
                    ext:bit "NHLFE_CREATED" {
                      position 24;
                    }
                    ext:bit "ILM_CREATED" {
                      position 25;
                    }
                    ext:bit "NEXTHOP_CHANGE" {
                      position 26;
                    }
                    ext:bit "Invaild" {
                      position 27;
                    }
                    ext:bit "SOURCE_CHANGE" {
                      position 28;
                    }
                    ext:bit "IN_SELECTEDQ" {
                      position 29;
                    }
                    ext:bit "EXITIF_ERROR" {
                      position 30;
                    }
                    ext:bit "GROUP_HEAD" {
                      position 31;
                    }
                }
                leaf ngAsIpString {
                  type string {
                    length "1..300";
                  }
                  config false;
                  description
                    "Ng Route prefix information.";
                }
                leaf ngPmsiString {
                  type string {
                    length "1..300";
                  }
                  config false;
                  description
                    "PMSI attribute.";
                }
                leaf advNextHop {
                  type inet:ip-address-no-zone;
                  config false;
                  description
                    "Next hop of an BGP.";
                }
              }
            }
            container ngRoutingTable2s {
              when "not(../afType='ipv4vpnmcast' or ../afType='mdt' or ../afType='vpntarget' or ../afType='vpnv4flow' or ../afType='vpnv6flow')";
              config false;
              description
                "List of displayed BGP Ng route type 2 information.";
              list ngRoutingTable2 {
                when "not(../../afType!='mvpn' and ../../afType!='mvpnv6')";
                key "ngNlri rd from ngRouteType routeTypeFlag";
                config false;
                description
                  "Information about BGP Ng routes type 2.";
                leaf ngNlri {
                  type inet:ipv4-address-no-zone;
                  config false;
                  description
                    "Prefix of a BGP route.";
                }
                leaf imTableId {
                  type uint32 {
                    range "0..4294967295";
                  }
                  config false;
                  description
                    "ID of the routing table to which routes are imported.";
                }
                leaf nexthop {
                  type inet:ip-address-no-zone;
                  config false;
                  description
                    "Next hop address to which packets are forwarded.";
                }
                leaf locPrf {
                  type uint32 {
                    range "0..4294967295";
                  }
                  config false;
                  description
                    "Local-preference.";
                }
                leaf prefVal {
                  type uint32 {
                    range "0..4294967295";
                  }
                  config false;
                  description
                    "Preferred value of a protocol.";
                }
                leaf prefrence {
                  type uint8 {
                    range "0..255";
                  }
                  config false;
                  description
                    "Priority of BGP routes.";
                }
                leaf pathAs {
                  type string {
                    length "1..300";
                  }
                  config false;
                  description
                    "List of the AS_Paths that packets pass through.";
                }
                leaf origin {
                  type bgpcommOrigin;
                  config false;
                  description
                    "Route origin.";
                }
                leaf med {
                  type uint32 {
                    range "0..4294967295";
                  }
                  config false;
                  description
                    "Route MED.";
                }
                leaf flagString {
                  type string {
                    length "1..100";
                  }
                  config false;
                  description
                    "Route flag that contains a string of characters.";
                }
                leaf rd {
                  type string {
                    length "1..22";
                  }
                  config false;
                  description
                    "Route distinguisher.";
                }
                leaf rtWorseReason {
                  type string {
                    length "1..50";
                  }
                  config false;
                  description
                    "Reason why a route is not selected.";
                }
                leaf peerString {
                  type string {
                    length "1..300";
                  }
                  config false;
                  description
                    "List of route sending peers.";
                }
                leaf time {
                  type uint32 {
                    range "0..4294967295";
                  }
                  config false;
                  description
                    "Time stamp of a route.";
                }
                leaf community {
                  type string {
                    length "1..120";
                  }
                  config false;
                  description
                    "Community attribute.";
                }
                leaf extCommunity {
                  type string {
                    length "1..300";
                  }
                  config false;
                  description
                    "Extended community attribute.";
                }
                leaf from {
                  type inet:ip-address-no-zone;
                  config false;
                  description
                    "Source peer that sends a route.";
                }
                leaf ifName {
                  type pub-type:ifName;
                  config false;
                  description
                    "Name of the outbound interface of a route.";
                }
                leaf originator {
                  type inet:ip-address-no-zone;
                  config false;
                  description
                    "Router ID of the route initiator.";
                }
                leaf clusterList {
                  type string {
                    length "1..300";
                  }
                  config false;
                  description
                    "List of cluster IDs.";
                }
                leaf remoteRouteId {
                  type inet:ipv4-address-no-zone;
                  config false;
                  description
                    "Router ID of a peer.";
                }
                leaf relayNexthop {
                  type inet:ip-address-no-zone;
                  config false;
                  description
                    "Next hop to which a route is iterated.";
                }
                leaf relaytnlName {
                  type string {
                    length "1..64";
                  }
                  config false;
                  description
                    "Name of a tunnel to which a route is iterated.";
                }
                leaf inLabel {
                  type uint32 {
                    range "0..4294967295";
                  }
                  config false;
                  description
                    "In-label.";
                }
                leaf outLabel {
                  type uint32 {
                    range "0..4294967295";
                  }
                  config false;
                  description
                    "Out-label.";
                }
                leaf ngRouteType {
                  type string {
                    length "1..50";
                  }
                  config false;
                  description
                    "Route type.";
                }
                leaf routeTypeFlag {
                  type pub-type:bits32;
                  config false;
                  description
                    "Route type.";
                  ext:masklen 32;
                    ext:bit "ibgp" {
                      position 0;
                    }
                    ext:bit "ebgp" {
                      position 1;
                    }
                    ext:bit "network" {
                      position 2;
                    }
                    ext:bit "import" {
                      position 3;
                    }
                    ext:bit "auto-summary" {
                      position 4;
                    }
                    ext:bit "aggregate" {
                      position 5;
                    }
                    ext:bit "cpri" {
                      position 6;
                    }
                    ext:bit "pcri" {
                      position 7;
                    }
                    ext:bit "suppressed" {
                      position 8;
                    }
                    ext:bit "NHP-EMPTY" {
                      position 9;
                    }
                    ext:bit "NO-ADV" {
                      position 10;
                    }
                    ext:bit "local_cross" {
                      position 11;
                    }
                    ext:bit "remote_cross" {
                      position 12;
                    }
                    ext:bit "VD-BGP" {
                      position 13;
                    }
                    ext:bit "PATH_LOCAL" {
                      position 14;
                    }
                    ext:bit "PATH_GATEWAY" {
                      position 15;
                    }
                    ext:bit "policy_nopass" {
                      position 16;
                    }
                    ext:bit "supprenet" {
                      position 17;
                    }
                    ext:bit "dampened" {
                      position 18;
                    }
                    ext:bit "history" {
                      position 19;
                    }
                    ext:bit "select" {
                      position 20;
                    }
                    ext:bit "best" {
                      position 21;
                    }
                    ext:bit "backup" {
                      position 22;
                    }
                    ext:bit "attr_change" {
                      position 23;
                    }
                    ext:bit "NHLFE_CREATED" {
                      position 24;
                    }
                    ext:bit "ILM_CREATED" {
                      position 25;
                    }
                    ext:bit "NEXTHOP_CHANGE" {
                      position 26;
                    }
                    ext:bit "Invaild" {
                      position 27;
                    }
                    ext:bit "SOURCE_CHANGE" {
                      position 28;
                    }
                    ext:bit "IN_SELECTEDQ" {
                      position 29;
                    }
                    ext:bit "EXITIF_ERROR" {
                      position 30;
                    }
                    ext:bit "GROUP_HEAD" {
                      position 31;
                    }
                }
                leaf ngAsIpString {
                  type string {
                    length "1..300";
                  }
                  config false;
                  description
                    "Ng Route Prefix Information.";
                }
                leaf advNextHop {
                  type inet:ip-address-no-zone;
                  config false;
                  description
                    "Next hop of an BGP.";
                }
              }
            }
            container ngRoutingTable3s {
              when "not(../afType='ipv4vpnmcast' or ../afType='mdt' or ../afType='vpntarget' or ../afType='vpnv4flow' or ../afType='vpnv6flow')";
              config false;
              description
                "List of displayed BGP Ng route type 3 information.";
              list ngRoutingTable3 {
                when "not(../../afType!='mvpn' and ../../afType!='mvpnv6')";
                key "ngNlri rd from ngRouteType routeTypeFlag";
                config false;
                description
                  "Information about BGP Ng routes type 3.";
                leaf ngNlri {
                  type inet:ipv4-address-no-zone;
                  config false;
                  description
                    "Prefix of a BGP route.";
                }
                leaf imTableId {
                  type uint32 {
                    range "0..4294967295";
                  }
                  config false;
                  description
                    "ID of the routing table to which routes are imported.";
                }
                leaf nexthop {
                  type inet:ip-address-no-zone;
                  config false;
                  description
                    "Next hop address to which packets are forwarded.";
                }
                leaf locPrf {
                  type uint32 {
                    range "0..4294967295";
                  }
                  config false;
                  description
                    "Local-preference.";
                }
                leaf prefVal {
                  type uint32 {
                    range "0..4294967295";
                  }
                  config false;
                  description
                    "Preferred value of a protocol.";
                }
                leaf prefrence {
                  type uint8 {
                    range "0..255";
                  }
                  config false;
                  description
                    "Priority of BGP routes.";
                }
                leaf pathAs {
                  type string {
                    length "1..300";
                  }
                  config false;
                  description
                    "List of the AS_Paths that packets pass through.";
                }
                leaf origin {
                  type bgpcommOrigin;
                  config false;
                  description
                    "Route origin.";
                }
                leaf med {
                  type uint32 {
                    range "0..4294967295";
                  }
                  config false;
                  description
                    "Route MED.";
                }
                leaf flagString {
                  type string {
                    length "1..100";
                  }
                  config false;
                  description
                    "Route flag that contains a string of characters.";
                }
                leaf rd {
                  type string {
                    length "1..22";
                  }
                  config false;
                  description
                    "Route distinguisher.";
                }
                leaf rtWorseReason {
                  type string {
                    length "1..50";
                  }
                  config false;
                  description
                    "Reason why a route is not selected.";
                }
                leaf peerString {
                  type string {
                    length "1..300";
                  }
                  config false;
                  description
                    "List of route sending peers.";
                }
                leaf time {
                  type uint32 {
                    range "0..4294967295";
                  }
                  config false;
                  description
                    "Time stamp of a route.";
                }
                leaf community {
                  type string {
                    length "1..120";
                  }
                  config false;
                  description
                    "Community attribute.";
                }
                leaf extCommunity {
                  type string {
                    length "1..300";
                  }
                  config false;
                  description
                    "Extended community attribute.";
                }
                leaf from {
                  type inet:ip-address-no-zone;
                  config false;
                  description
                    "Source peer that sends a route.";
                }
                leaf ifName {
                  type pub-type:ifName;
                  config false;
                  description
                    "Name of the outbound interface of a route.";
                }
                leaf originator {
                  type inet:ip-address-no-zone;
                  config false;
                  description
                    "Router ID of the route initiator.";
                }
                leaf clusterList {
                  type string {
                    length "1..300";
                  }
                  config false;
                  description
                    "List of cluster IDs.";
                }
                leaf remoteRouteId {
                  type inet:ipv4-address-no-zone;
                  config false;
                  description
                    "Router ID of a peer.";
                }
                leaf relayNexthop {
                  type inet:ip-address-no-zone;
                  config false;
                  description
                    "Next hop to which a route is iterated.";
                }
                leaf relaytnlName {
                  type string {
                    length "1..64";
                  }
                  config false;
                  description
                    "Name of a tunnel to which a route is iterated.";
                }
                leaf inLabel {
                  type uint32 {
                    range "0..4294967295";
                  }
                  config false;
                  description
                    "In-label.";
                }
                leaf outLabel {
                  type uint32 {
                    range "0..4294967295";
                  }
                  config false;
                  description
                    "Out-label.";
                }
                leaf ngRouteType {
                  type string {
                    length "1..50";
                  }
                  config false;
                  description
                    "Route type.";
                }
                leaf routeTypeFlag {
                  type pub-type:bits32;
                  config false;
                  description
                    "Route type.";
                  ext:masklen 32;
                    ext:bit "ibgp" {
                      position 0;
                    }
                    ext:bit "ebgp" {
                      position 1;
                    }
                    ext:bit "network" {
                      position 2;
                    }
                    ext:bit "import" {
                      position 3;
                    }
                    ext:bit "auto-summary" {
                      position 4;
                    }
                    ext:bit "aggregate" {
                      position 5;
                    }
                    ext:bit "cpri" {
                      position 6;
                    }
                    ext:bit "pcri" {
                      position 7;
                    }
                    ext:bit "suppressed" {
                      position 8;
                    }
                    ext:bit "NHP-EMPTY" {
                      position 9;
                    }
                    ext:bit "NO-ADV" {
                      position 10;
                    }
                    ext:bit "local_cross" {
                      position 11;
                    }
                    ext:bit "remote_cross" {
                      position 12;
                    }
                    ext:bit "VD-BGP" {
                      position 13;
                    }
                    ext:bit "PATH_LOCAL" {
                      position 14;
                    }
                    ext:bit "PATH_GATEWAY" {
                      position 15;
                    }
                    ext:bit "policy_nopass" {
                      position 16;
                    }
                    ext:bit "supprenet" {
                      position 17;
                    }
                    ext:bit "dampened" {
                      position 18;
                    }
                    ext:bit "history" {
                      position 19;
                    }
                    ext:bit "select" {
                      position 20;
                    }
                    ext:bit "best" {
                      position 21;
                    }
                    ext:bit "backup" {
                      position 22;
                    }
                    ext:bit "attr_change" {
                      position 23;
                    }
                    ext:bit "NHLFE_CREATED" {
                      position 24;
                    }
                    ext:bit "ILM_CREATED" {
                      position 25;
                    }
                    ext:bit "NEXTHOP_CHANGE" {
                      position 26;
                    }
                    ext:bit "Invaild" {
                      position 27;
                    }
                    ext:bit "SOURCE_CHANGE" {
                      position 28;
                    }
                    ext:bit "IN_SELECTEDQ" {
                      position 29;
                    }
                    ext:bit "EXITIF_ERROR" {
                      position 30;
                    }
                    ext:bit "GROUP_HEAD" {
                      position 31;
                    }
                }
                leaf ngAsIpString {
                  type string {
                    length "1..300";
                  }
                  config false;
                  description
                    "Ng route prefix information.";
                }
                leaf advNextHop {
                  type inet:ip-address-no-zone;
                  config false;
                  description
                    "Next hop of an BGP.";
                }
              }
            }
            container ngRoutingTable4s {
              when "not(../afType='ipv4vpnmcast' or ../afType='mdt' or ../afType='vpntarget' or ../afType='vpnv4flow' or ../afType='vpnv6flow')";
              config false;
              description
                "List of displayed BGP Ng route type 4 information.";
              list ngRoutingTable4 {
                when "not(../../afType!='mvpn' and ../../afType!='mvpnv6')";
                key "ngNlri rd from ngRouteType routeTypeFlag";
                config false;
                description
                  "Information about BGP Ng routes type 4.";
                leaf ngNlri {
                  type inet:ipv4-address-no-zone;
                  config false;
                  description
                    "Prefix of a BGP route.";
                }
                leaf imTableId {
                  type uint32 {
                    range "0..4294967295";
                  }
                  config false;
                  description
                    "ID of the routing table to which routes are imported.";
                }
                leaf nexthop {
                  type inet:ip-address-no-zone;
                  config false;
                  description
                    "Next hop address to which packets are forwarded.";
                }
                leaf locPrf {
                  type uint32 {
                    range "0..4294967295";
                  }
                  config false;
                  description
                    "Local-preference.";
                }
                leaf prefVal {
                  type uint32 {
                    range "0..4294967295";
                  }
                  config false;
                  description
                    "Preferred value of a protocol.";
                }
                leaf prefrence {
                  type uint8 {
                    range "0..255";
                  }
                  config false;
                  description
                    "Priority of BGP routes.";
                }
                leaf pathAs {
                  type string {
                    length "1..300";
                  }
                  config false;
                  description
                    "List of the AS_Paths that packets pass through.";
                }
                leaf origin {
                  type bgpcommOrigin;
                  config false;
                  description
                    "Route origin.";
                }
                leaf med {
                  type uint32 {
                    range "0..4294967295";
                  }
                  config false;
                  description
                    "Route MED.";
                }
                leaf flagString {
                  type string {
                    length "1..100";
                  }
                  config false;
                  description
                    "Route flag that contains a string of characters.";
                }
                leaf rd {
                  type string {
                    length "1..22";
                  }
                  config false;
                  description
                    "Route distinguisher.";
                }
                leaf rtWorseReason {
                  type string {
                    length "1..50";
                  }
                  config false;
                  description
                    "Reason why a route is not selected.";
                }
                leaf peerString {
                  type string {
                    length "1..300";
                  }
                  config false;
                  description
                    "List of route sending peers.";
                }
                leaf time {
                  type uint32 {
                    range "0..4294967295";
                  }
                  config false;
                  description
                    "Time stamp of a route.";
                }
                leaf community {
                  type string {
                    length "1..120";
                  }
                  config false;
                  description
                    "Community attribute.";
                }
                leaf extCommunity {
                  type string {
                    length "1..300";
                  }
                  config false;
                  description
                    "Extended community attribute.";
                }
                leaf from {
                  type inet:ip-address-no-zone;
                  config false;
                  description
                    "Source peer that sends a route.";
                }
                leaf ifName {
                  type pub-type:ifName;
                  config false;
                  description
                    "Name of the outbound interface of a route.";
                }
                leaf originator {
                  type inet:ip-address-no-zone;
                  config false;
                  description
                    "Router ID of the route initiator.";
                }
                leaf clusterList {
                  type string {
                    length "1..300";
                  }
                  config false;
                  description
                    "List of cluster IDs.";
                }
                leaf remoteRouteId {
                  type inet:ipv4-address-no-zone;
                  config false;
                  description
                    "Router ID of a peer.";
                }
                leaf relayNexthop {
                  type inet:ip-address-no-zone;
                  config false;
                  description
                    "Next hop to which a route is iterated.";
                }
                leaf relaytnlName {
                  type string {
                    length "1..64";
                  }
                  config false;
                  description
                    "Name of a tunnel to which a route is iterated.";
                }
                leaf inLabel {
                  type uint32 {
                    range "0..4294967295";
                  }
                  config false;
                  description
                    "In-label.";
                }
                leaf outLabel {
                  type uint32 {
                    range "0..4294967295";
                  }
                  config false;
                  description
                    "Out-label.";
                }
                leaf ngRouteType {
                  type string {
                    length "1..50";
                  }
                  config false;
                  description
                    "Route type.";
                }
                leaf routeTypeFlag {
                  type pub-type:bits32;
                  config false;
                  description
                    "Route type.";
                  ext:masklen 32;
                    ext:bit "ibgp" {
                      position 0;
                    }
                    ext:bit "ebgp" {
                      position 1;
                    }
                    ext:bit "network" {
                      position 2;
                    }
                    ext:bit "import" {
                      position 3;
                    }
                    ext:bit "auto-summary" {
                      position 4;
                    }
                    ext:bit "aggregate" {
                      position 5;
                    }
                    ext:bit "cpri" {
                      position 6;
                    }
                    ext:bit "pcri" {
                      position 7;
                    }
                    ext:bit "suppressed" {
                      position 8;
                    }
                    ext:bit "NHP-EMPTY" {
                      position 9;
                    }
                    ext:bit "NO-ADV" {
                      position 10;
                    }
                    ext:bit "local_cross" {
                      position 11;
                    }
                    ext:bit "remote_cross" {
                      position 12;
                    }
                    ext:bit "VD-BGP" {
                      position 13;
                    }
                    ext:bit "PATH_LOCAL" {
                      position 14;
                    }
                    ext:bit "PATH_GATEWAY" {
                      position 15;
                    }
                    ext:bit "policy_nopass" {
                      position 16;
                    }
                    ext:bit "supprenet" {
                      position 17;
                    }
                    ext:bit "dampened" {
                      position 18;
                    }
                    ext:bit "history" {
                      position 19;
                    }
                    ext:bit "select" {
                      position 20;
                    }
                    ext:bit "best" {
                      position 21;
                    }
                    ext:bit "backup" {
                      position 22;
                    }
                    ext:bit "attr_change" {
                      position 23;
                    }
                    ext:bit "NHLFE_CREATED" {
                      position 24;
                    }
                    ext:bit "ILM_CREATED" {
                      position 25;
                    }
                    ext:bit "NEXTHOP_CHANGE" {
                      position 26;
                    }
                    ext:bit "Invaild" {
                      position 27;
                    }
                    ext:bit "SOURCE_CHANGE" {
                      position 28;
                    }
                    ext:bit "IN_SELECTEDQ" {
                      position 29;
                    }
                    ext:bit "EXITIF_ERROR" {
                      position 30;
                    }
                    ext:bit "GROUP_HEAD" {
                      position 31;
                    }
                }
                leaf ngAsIpString {
                  type string {
                    length "1..300";
                  }
                  config false;
                  description
                    "Ng route prefix information.";
                }
                leaf advNextHop {
                  type inet:ip-address-no-zone;
                  config false;
                  description
                    "Next hop of an BGP.";
                }
              }
            }
            container ngRoutingTable5s {
              when "not(../afType='ipv4vpnmcast' or ../afType='mdt' or ../afType='vpntarget' or ../afType='vpnv4flow' or ../afType='vpnv6flow')";
              config false;
              description
                "List of displayed BGP Ng route type 5 information.";
              list ngRoutingTable5 {
                when "not(../../afType!='mvpn' and ../../afType!='mvpnv6')";
                key "ngNlri rd from ngRouteType routeTypeFlag";
                config false;
                description
                  "Information about BGP Ng routes type 5.";
                leaf ngNlri {
                  type inet:ipv4-address-no-zone;
                  config false;
                  description
                    "Prefix of a BGP route.";
                }
                leaf imTableId {
                  type uint32 {
                    range "0..4294967295";
                  }
                  config false;
                  description
                    "ID of the routing table to which routes are imported.";
                }
                leaf nexthop {
                  type inet:ip-address-no-zone;
                  config false;
                  description
                    "Next hop address to which packets are forwarded.";
                }
                leaf locPrf {
                  type uint32 {
                    range "0..4294967295";
                  }
                  config false;
                  description
                    "Local-preference.";
                }
                leaf prefVal {
                  type uint32 {
                    range "0..4294967295";
                  }
                  config false;
                  description
                    "Preferred value of a protocol.";
                }
                leaf prefrence {
                  type uint8 {
                    range "0..255";
                  }
                  config false;
                  description
                    "Priority of BGP routes.";
                }
                leaf pathAs {
                  type string {
                    length "1..300";
                  }
                  config false;
                  description
                    "List of the AS_Paths that packets pass through.";
                }
                leaf origin {
                  type bgpcommOrigin;
                  config false;
                  description
                    "Route origin.";
                }
                leaf med {
                  type uint32 {
                    range "0..4294967295";
                  }
                  config false;
                  description
                    "Route MED.";
                }
                leaf flagString {
                  type string {
                    length "1..100";
                  }
                  config false;
                  description
                    "Route flag that contains a string of characters.";
                }
                leaf rd {
                  type string {
                    length "1..22";
                  }
                  config false;
                  description
                    "Route distinguisher.";
                }
                leaf rtWorseReason {
                  type string {
                    length "1..50";
                  }
                  config false;
                  description
                    "Reason why a route is not selected.";
                }
                leaf peerString {
                  type string {
                    length "1..300";
                  }
                  config false;
                  description
                    "List of route sending peers.";
                }
                leaf time {
                  type uint32 {
                    range "0..4294967295";
                  }
                  config false;
                  description
                    "Time stamp of a route.";
                }
                leaf community {
                  type string {
                    length "1..120";
                  }
                  config false;
                  description
                    "Community attribute.";
                }
                leaf extCommunity {
                  type string {
                    length "1..300";
                  }
                  config false;
                  description
                    "Extended community attribute.";
                }
                leaf from {
                  type inet:ip-address-no-zone;
                  config false;
                  description
                    "Source peer that sends a route.";
                }
                leaf ifName {
                  type pub-type:ifName;
                  config false;
                  description
                    "Name of the outbound interface of a route.";
                }
                leaf originator {
                  type inet:ip-address-no-zone;
                  config false;
                  description
                    "Router ID of the route initiator.";
                }
                leaf clusterList {
                  type string {
                    length "1..300";
                  }
                  config false;
                  description
                    "List of cluster IDs.";
                }
                leaf remoteRouteId {
                  type inet:ipv4-address-no-zone;
                  config false;
                  description
                    "Router ID of a peer.";
                }
                leaf relayNexthop {
                  type inet:ip-address-no-zone;
                  config false;
                  description
                    "Next hop to which a route is iterated.";
                }
                leaf relaytnlName {
                  type string {
                    length "1..64";
                  }
                  config false;
                  description
                    "Name of a tunnel to which a route is iterated.";
                }
                leaf inLabel {
                  type uint32 {
                    range "0..4294967295";
                  }
                  config false;
                  description
                    "In-label.";
                }
                leaf outLabel {
                  type uint32 {
                    range "0..4294967295";
                  }
                  config false;
                  description
                    "Out-label.";
                }
                leaf ngRouteType {
                  type string {
                    length "1..50";
                  }
                  config false;
                  description
                    "Route type.";
                }
                leaf routeTypeFlag {
                  type pub-type:bits32;
                  config false;
                  description
                    "Route type.";
                  ext:masklen 32;
                    ext:bit "ibgp" {
                      position 0;
                    }
                    ext:bit "ebgp" {
                      position 1;
                    }
                    ext:bit "network" {
                      position 2;
                    }
                    ext:bit "import" {
                      position 3;
                    }
                    ext:bit "auto-summary" {
                      position 4;
                    }
                    ext:bit "aggregate" {
                      position 5;
                    }
                    ext:bit "cpri" {
                      position 6;
                    }
                    ext:bit "pcri" {
                      position 7;
                    }
                    ext:bit "suppressed" {
                      position 8;
                    }
                    ext:bit "NHP-EMPTY" {
                      position 9;
                    }
                    ext:bit "NO-ADV" {
                      position 10;
                    }
                    ext:bit "local_cross" {
                      position 11;
                    }
                    ext:bit "remote_cross" {
                      position 12;
                    }
                    ext:bit "VD-BGP" {
                      position 13;
                    }
                    ext:bit "PATH_LOCAL" {
                      position 14;
                    }
                    ext:bit "PATH_GATEWAY" {
                      position 15;
                    }
                    ext:bit "policy_nopass" {
                      position 16;
                    }
                    ext:bit "supprenet" {
                      position 17;
                    }
                    ext:bit "dampened" {
                      position 18;
                    }
                    ext:bit "history" {
                      position 19;
                    }
                    ext:bit "select" {
                      position 20;
                    }
                    ext:bit "best" {
                      position 21;
                    }
                    ext:bit "backup" {
                      position 22;
                    }
                    ext:bit "attr_change" {
                      position 23;
                    }
                    ext:bit "NHLFE_CREATED" {
                      position 24;
                    }
                    ext:bit "ILM_CREATED" {
                      position 25;
                    }
                    ext:bit "NEXTHOP_CHANGE" {
                      position 26;
                    }
                    ext:bit "Invaild" {
                      position 27;
                    }
                    ext:bit "SOURCE_CHANGE" {
                      position 28;
                    }
                    ext:bit "IN_SELECTEDQ" {
                      position 29;
                    }
                    ext:bit "EXITIF_ERROR" {
                      position 30;
                    }
                    ext:bit "GROUP_HEAD" {
                      position 31;
                    }
                }
                leaf ngAsIpString {
                  type string {
                    length "1..300";
                  }
                  config false;
                  description
                    "Ng route prefix information.";
                }
                leaf advNextHop {
                  type inet:ip-address-no-zone;
                  config false;
                  description
                    "Next hop of an BGP.";
                }
              }
            }
            container ngRoutingTable6s {
              when "not(../afType='ipv4vpnmcast' or ../afType='mdt' or ../afType='vpntarget' or ../afType='vpnv4flow' or ../afType='vpnv6flow')";
              config false;
              description
                "List of displayed BGP Ng route type 6 information.";
              list ngRoutingTable6 {
                when "not(../../afType!='mvpn' and ../../afType!='mvpnv6')";
                key "ngNlri rd from ngRouteType routeTypeFlag";
                config false;
                description
                  "Information about BGP Ng routes type 6.";
                leaf ngNlri {
                  type inet:ipv4-address-no-zone;
                  config false;
                  description
                    "Prefix of a BGP route.";
                }
                leaf imTableId {
                  type uint32 {
                    range "0..4294967295";
                  }
                  config false;
                  description
                    "ID of the routing table to which routes are imported.";
                }
                leaf nexthop {
                  type inet:ip-address-no-zone;
                  config false;
                  description
                    "Next hop address to which packets are forwarded.";
                }
                leaf locPrf {
                  type uint32 {
                    range "0..4294967295";
                  }
                  config false;
                  description
                    "Local-preference.";
                }
                leaf prefVal {
                  type uint32 {
                    range "0..4294967295";
                  }
                  config false;
                  description
                    "Preferred value of a protocol.";
                }
                leaf prefrence {
                  type uint8 {
                    range "0..255";
                  }
                  config false;
                  description
                    "Priority of BGP routes.";
                }
                leaf pathAs {
                  type string {
                    length "1..300";
                  }
                  config false;
                  description
                    "List of the AS_Paths that packets pass through.";
                }
                leaf origin {
                  type bgpcommOrigin;
                  config false;
                  description
                    "Route origin.";
                }
                leaf med {
                  type uint32 {
                    range "0..4294967295";
                  }
                  config false;
                  description
                    "Route MED.";
                }
                leaf flagString {
                  type string {
                    length "1..100";
                  }
                  config false;
                  description
                    "Route flag that contains a string of characters.";
                }
                leaf rd {
                  type string {
                    length "1..22";
                  }
                  config false;
                  description
                    "Route distinguisher.";
                }
                leaf rtWorseReason {
                  type string {
                    length "1..50";
                  }
                  config false;
                  description
                    "Reason why a route is not selected.";
                }
                leaf peerString {
                  type string {
                    length "1..300";
                  }
                  config false;
                  description
                    "List of route sending peers.";
                }
                leaf time {
                  type uint32 {
                    range "0..4294967295";
                  }
                  config false;
                  description
                    "Time stamp of a route.";
                }
                leaf community {
                  type string {
                    length "1..120";
                  }
                  config false;
                  description
                    "Community attribute.";
                }
                leaf extCommunity {
                  type string {
                    length "1..300";
                  }
                  config false;
                  description
                    "Extended community attribute.";
                }
                leaf from {
                  type inet:ip-address-no-zone;
                  config false;
                  description
                    "Source peer that sends a route.";
                }
                leaf ifName {
                  type pub-type:ifName;
                  config false;
                  description
                    "Name of the outbound interface of a route.";
                }
                leaf originator {
                  type inet:ip-address-no-zone;
                  config false;
                  description
                    "Router ID of the route initiator.";
                }
                leaf clusterList {
                  type string {
                    length "1..300";
                  }
                  config false;
                  description
                    "List of cluster IDs.";
                }
                leaf remoteRouteId {
                  type inet:ipv4-address-no-zone;
                  config false;
                  description
                    "Router ID of a peer.";
                }
                leaf relayNexthop {
                  type inet:ip-address-no-zone;
                  config false;
                  description
                    "Next hop to which a route is iterated.";
                }
                leaf relaytnlName {
                  type string {
                    length "1..64";
                  }
                  config false;
                  description
                    "Name of a tunnel to which a route is iterated.";
                }
                leaf inLabel {
                  type uint32 {
                    range "0..4294967295";
                  }
                  config false;
                  description
                    "In-label.";
                }
                leaf outLabel {
                  type uint32 {
                    range "0..4294967295";
                  }
                  config false;
                  description
                    "Out-label.";
                }
                leaf ngRouteType {
                  type string {
                    length "1..50";
                  }
                  config false;
                  description
                    "Route type.";
                }
                leaf routeTypeFlag {
                  type pub-type:bits32;
                  config false;
                  description
                    "Route type.";
                  ext:masklen 32;
                    ext:bit "ibgp" {
                      position 0;
                    }
                    ext:bit "ebgp" {
                      position 1;
                    }
                    ext:bit "network" {
                      position 2;
                    }
                    ext:bit "import" {
                      position 3;
                    }
                    ext:bit "auto-summary" {
                      position 4;
                    }
                    ext:bit "aggregate" {
                      position 5;
                    }
                    ext:bit "cpri" {
                      position 6;
                    }
                    ext:bit "pcri" {
                      position 7;
                    }
                    ext:bit "suppressed" {
                      position 8;
                    }
                    ext:bit "NHP-EMPTY" {
                      position 9;
                    }
                    ext:bit "NO-ADV" {
                      position 10;
                    }
                    ext:bit "local_cross" {
                      position 11;
                    }
                    ext:bit "remote_cross" {
                      position 12;
                    }
                    ext:bit "VD-BGP" {
                      position 13;
                    }
                    ext:bit "PATH_LOCAL" {
                      position 14;
                    }
                    ext:bit "PATH_GATEWAY" {
                      position 15;
                    }
                    ext:bit "policy_nopass" {
                      position 16;
                    }
                    ext:bit "supprenet" {
                      position 17;
                    }
                    ext:bit "dampened" {
                      position 18;
                    }
                    ext:bit "history" {
                      position 19;
                    }
                    ext:bit "select" {
                      position 20;
                    }
                    ext:bit "best" {
                      position 21;
                    }
                    ext:bit "backup" {
                      position 22;
                    }
                    ext:bit "attr_change" {
                      position 23;
                    }
                    ext:bit "NHLFE_CREATED" {
                      position 24;
                    }
                    ext:bit "ILM_CREATED" {
                      position 25;
                    }
                    ext:bit "NEXTHOP_CHANGE" {
                      position 26;
                    }
                    ext:bit "Invaild" {
                      position 27;
                    }
                    ext:bit "SOURCE_CHANGE" {
                      position 28;
                    }
                    ext:bit "IN_SELECTEDQ" {
                      position 29;
                    }
                    ext:bit "EXITIF_ERROR" {
                      position 30;
                    }
                    ext:bit "GROUP_HEAD" {
                      position 31;
                    }
                }
                leaf ngAsIpString {
                  type string {
                    length "1..300";
                  }
                  config false;
                  description
                    "Ng route prefix information.";
                }
                leaf advNextHop {
                  type inet:ip-address-no-zone;
                  config false;
                  description
                    "Next hop of an BGP.";
                }
              }
            }
            container ngRoutingTable7s {
              when "not(../afType='ipv4vpnmcast' or ../afType='mdt' or ../afType='vpntarget' or ../afType='vpnv4flow' or ../afType='vpnv6flow')";
              config false;
              description
                "List of displayed BGP Ng route type 7 information.";
              list ngRoutingTable7 {
                when "not(../../afType!='mvpn' and ../../afType!='mvpnv6')";
                key "ngNlri rd from ngRouteType routeTypeFlag";
                config false;
                description
                  "Information about BGP Ng routes type 7.";
                leaf ngNlri {
                  type inet:ipv4-address-no-zone;
                  config false;
                  description
                    "Prefix of a BGP route.";
                }
                leaf imTableId {
                  type uint32 {
                    range "0..4294967295";
                  }
                  config false;
                  description
                    "ID of the routing table to which routes are imported.";
                }
                leaf nexthop {
                  type inet:ip-address-no-zone;
                  config false;
                  description
                    "Next hop address to which packets are forwarded.";
                }
                leaf locPrf {
                  type uint32 {
                    range "0..4294967295";
                  }
                  config false;
                  description
                    "Local-preference.";
                }
                leaf prefVal {
                  type uint32 {
                    range "0..4294967295";
                  }
                  config false;
                  description
                    "Preferred value of a protocol.";
                }
                leaf prefrence {
                  type uint8 {
                    range "0..255";
                  }
                  config false;
                  description
                    "Priority of BGP routes.";
                }
                leaf pathAs {
                  type string {
                    length "1..300";
                  }
                  config false;
                  description
                    "List of the AS_Paths that packets pass through.";
                }
                leaf origin {
                  type bgpcommOrigin;
                  config false;
                  description
                    "Route origin.";
                }
                leaf med {
                  type uint32 {
                    range "0..4294967295";
                  }
                  config false;
                  description
                    "Route MED.";
                }
                leaf flagString {
                  type string {
                    length "1..100";
                  }
                  config false;
                  description
                    "Route flag that contains a string of characters.";
                }
                leaf rd {
                  type string {
                    length "1..22";
                  }
                  config false;
                  description
                    "Route distinguisher.";
                }
                leaf rtWorseReason {
                  type string {
                    length "1..50";
                  }
                  config false;
                  description
                    "Reason why a route is not selected.";
                }
                leaf peerString {
                  type string {
                    length "1..300";
                  }
                  config false;
                  description
                    "List of route sending peers.";
                }
                leaf time {
                  type uint32 {
                    range "0..4294967295";
                  }
                  config false;
                  description
                    "Time stamp of a route.";
                }
                leaf community {
                  type string {
                    length "1..120";
                  }
                  config false;
                  description
                    "Community attribute.";
                }
                leaf extCommunity {
                  type string {
                    length "1..300";
                  }
                  config false;
                  description
                    "Extended community attribute.";
                }
                leaf from {
                  type inet:ip-address-no-zone;
                  config false;
                  description
                    "Source peer that sends a route.";
                }
                leaf ifName {
                  type pub-type:ifName;
                  config false;
                  description
                    "Name of the outbound interface of a route.";
                }
                leaf originator {
                  type inet:ip-address-no-zone;
                  config false;
                  description
                    "Router ID of the route initiator.";
                }
                leaf clusterList {
                  type string {
                    length "1..300";
                  }
                  config false;
                  description
                    "List of cluster IDs.";
                }
                leaf remoteRouteId {
                  type inet:ipv4-address-no-zone;
                  config false;
                  description
                    "Router ID of a peer.";
                }
                leaf relayNexthop {
                  type inet:ip-address-no-zone;
                  config false;
                  description
                    "Next hop to which a route is iterated.";
                }
                leaf relaytnlName {
                  type string {
                    length "1..64";
                  }
                  config false;
                  description
                    "Name of a tunnel to which a route is iterated.";
                }
                leaf inLabel {
                  type uint32 {
                    range "0..4294967295";
                  }
                  config false;
                  description
                    "In-label.";
                }
                leaf outLabel {
                  type uint32 {
                    range "0..4294967295";
                  }
                  config false;
                  description
                    "Out-label.";
                }
                leaf ngRouteType {
                  type string {
                    length "1..50";
                  }
                  config false;
                  description
                    "Route type.";
                }
                leaf routeTypeFlag {
                  type pub-type:bits32;
                  config false;
                  description
                    "Route type.";
                  ext:masklen 32;
                    ext:bit "ibgp" {
                      position 0;
                    }
                    ext:bit "ebgp" {
                      position 1;
                    }
                    ext:bit "network" {
                      position 2;
                    }
                    ext:bit "import" {
                      position 3;
                    }
                    ext:bit "auto-summary" {
                      position 4;
                    }
                    ext:bit "aggregate" {
                      position 5;
                    }
                    ext:bit "cpri" {
                      position 6;
                    }
                    ext:bit "pcri" {
                      position 7;
                    }
                    ext:bit "suppressed" {
                      position 8;
                    }
                    ext:bit "NHP-EMPTY" {
                      position 9;
                    }
                    ext:bit "NO-ADV" {
                      position 10;
                    }
                    ext:bit "local_cross" {
                      position 11;
                    }
                    ext:bit "remote_cross" {
                      position 12;
                    }
                    ext:bit "VD-BGP" {
                      position 13;
                    }
                    ext:bit "PATH_LOCAL" {
                      position 14;
                    }
                    ext:bit "PATH_GATEWAY" {
                      position 15;
                    }
                    ext:bit "policy_nopass" {
                      position 16;
                    }
                    ext:bit "supprenet" {
                      position 17;
                    }
                    ext:bit "dampened" {
                      position 18;
                    }
                    ext:bit "history" {
                      position 19;
                    }
                    ext:bit "select" {
                      position 20;
                    }
                    ext:bit "best" {
                      position 21;
                    }
                    ext:bit "backup" {
                      position 22;
                    }
                    ext:bit "attr_change" {
                      position 23;
                    }
                    ext:bit "NHLFE_CREATED" {
                      position 24;
                    }
                    ext:bit "ILM_CREATED" {
                      position 25;
                    }
                    ext:bit "NEXTHOP_CHANGE" {
                      position 26;
                    }
                    ext:bit "Invaild" {
                      position 27;
                    }
                    ext:bit "SOURCE_CHANGE" {
                      position 28;
                    }
                    ext:bit "IN_SELECTEDQ" {
                      position 29;
                    }
                    ext:bit "EXITIF_ERROR" {
                      position 30;
                    }
                    ext:bit "GROUP_HEAD" {
                      position 31;
                    }
                }
                leaf ngAsIpString {
                  type string {
                    length "1..300";
                  }
                  config false;
                  description
                    "Ng route prefix information.";
                }
                leaf advNextHop {
                  type inet:ip-address-no-zone;
                  config false;
                  description
                    "Next hop of an BGP.";
                }
              }
            }
            container l2vpnAdVplsRoutingTables {
              when "not(../afType='ipv4vpnmcast' or ../afType='mdt' or ../afType='vpntarget')";
              config false;
              description
                "List of displayed BGP L2VPN-AD Vpls route information.";
              list l2vpnAdVplsRoutingTable {
                when "not(../../afType='rpd' or ../../afType='vpnv4flow' or ../../afType='vpnv6flow') or ../../afType='l2vpnad'";
                key "routeTypeFlag imTableId rd from";
                config false;
                description
                  "Information about BGP L2VPN-AD Vpls routes.";
                leaf l2vpnAdNlri {
                  type string {
                    length "1..50";
                  }
                  config false;
                  description
                    "Prefix of a BGP route.";
                }
                leaf routeTypeFlag {
                  type pub-type:bits32;
                  config false;
                  description
                    "Route type.";
                  ext:masklen 32;
                    ext:bit "ibgp" {
                      position 0;
                    }
                    ext:bit "ebgp" {
                      position 1;
                    }
                    ext:bit "network" {
                      position 2;
                    }
                    ext:bit "import" {
                      position 3;
                    }
                    ext:bit "auto-summary" {
                      position 4;
                    }
                    ext:bit "aggregate" {
                      position 5;
                    }
                    ext:bit "cpri" {
                      position 6;
                    }
                    ext:bit "pcri" {
                      position 7;
                    }
                    ext:bit "suppressed" {
                      position 8;
                    }
                    ext:bit "NHP-EMPTY" {
                      position 9;
                    }
                    ext:bit "NO-ADV" {
                      position 10;
                    }
                    ext:bit "local_cross" {
                      position 11;
                    }
                    ext:bit "remote_cross" {
                      position 12;
                    }
                    ext:bit "VD-BGP" {
                      position 13;
                    }
                    ext:bit "PATH_LOCAL" {
                      position 14;
                    }
                    ext:bit "PATH_GATEWAY" {
                      position 15;
                    }
                    ext:bit "policy_nopass" {
                      position 16;
                    }
                    ext:bit "supprenet" {
                      position 17;
                    }
                    ext:bit "dampened" {
                      position 18;
                    }
                    ext:bit "history" {
                      position 19;
                    }
                    ext:bit "select" {
                      position 20;
                    }
                    ext:bit "best" {
                      position 21;
                    }
                    ext:bit "backup" {
                      position 22;
                    }
                    ext:bit "attr_change" {
                      position 23;
                    }
                    ext:bit "NHLFE_CREATED" {
                      position 24;
                    }
                    ext:bit "ILM_CREATED" {
                      position 25;
                    }
                    ext:bit "NEXTHOP_CHANGE" {
                      position 26;
                    }
                    ext:bit "Invaild" {
                      position 27;
                    }
                    ext:bit "SOURCE_CHANGE" {
                      position 28;
                    }
                    ext:bit "IN_SELECTEDQ" {
                      position 29;
                    }
                    ext:bit "EXITIF_ERROR" {
                      position 30;
                    }
                    ext:bit "GROUP_HEAD" {
                      position 31;
                    }
                }
                leaf imTableId {
                  type uint32 {
                    range "0..4294967295";
                  }
                  config false;
                  description
                    "ID of the routing table to which routes are imported.";
                }
                leaf nexthop {
                  type inet:ip-address-no-zone;
                  config false;
                  description
                    "Next hop address to which packets are forwarded.";
                }
                leaf locPrf {
                  type uint32 {
                    range "0..4294967295";
                  }
                  config false;
                  description
                    "Local-preference.";
                }
                leaf prefVal {
                  type uint32 {
                    range "0..4294967295";
                  }
                  config false;
                  description
                    "Preferred value of a protocol.";
                }
                leaf prefrence {
                  type uint8 {
                    range "0..255";
                  }
                  config false;
                  description
                    "Priority of BGP routes.";
                }
                leaf pathAs {
                  type string {
                    length "1..300";
                  }
                  config false;
                  description
                    "List of the AS_Paths that packets pass through.";
                }
                leaf origin {
                  type bgpcommOrigin;
                  config false;
                  description
                    "Route origin.";
                }
                leaf med {
                  type uint32 {
                    range "0..4294967295";
                  }
                  config false;
                  description
                    "Route MED.";
                }
                leaf flagString {
                  type string {
                    length "1..100";
                  }
                  config false;
                  description
                    "Route flag that contains a string of characters.";
                }
                leaf rd {
                  type string {
                    length "1..22";
                  }
                  config false;
                  description
                    "Route distinguisher.";
                }
                leaf rtWorseReason {
                  type string {
                    length "1..50";
                  }
                  config false;
                  description
                    "Reason why a route is not selected.";
                }
                leaf peerString {
                  type string {
                    length "1..300";
                  }
                  config false;
                  description
                    "List of route sending peers.";
                }
                leaf time {
                  type uint32 {
                    range "0..4294967295";
                  }
                  config false;
                  description
                    "Time stamp of a route.";
                }
                leaf community {
                  type string {
                    length "1..120";
                  }
                  config false;
                  description
                    "Community attribute.";
                }
                leaf extCommunity {
                  type string {
                    length "1..300";
                  }
                  config false;
                  description
                    "Extended community attribute.";
                }
                leaf from {
                  type inet:ip-address-no-zone;
                  config false;
                  description
                    "Source peer that sends a route.";
                }
                leaf ifName {
                  type pub-type:ifName;
                  config false;
                  description
                    "Name of the outbound interface of a route.";
                }
                leaf originator {
                  type inet:ip-address-no-zone;
                  config false;
                  description
                    "Router ID of the route initiator.";
                }
                leaf clusterList {
                  type string {
                    length "1..300";
                  }
                  config false;
                  description
                    "List of cluster IDs.";
                }
                leaf remoteRouteId {
                  type inet:ipv4-address-no-zone;
                  config false;
                  description
                    "Router ID of a peer.";
                }
                leaf relayNexthop {
                  type inet:ip-address-no-zone;
                  config false;
                  description
                    "Next hop to which a route is iterated.";
                }
                leaf relaytnlName {
                  type string {
                    length "1..64";
                  }
                  config false;
                  description
                    "Name of a tunnel to which a route is iterated.";
                }
                leaf inLabel {
                  type uint32 {
                    range "0..4294967295";
                  }
                  config false;
                  description
                    "In-label.";
                }
                leaf outLabel {
                  type uint32 {
                    range "0..4294967295";
                  }
                  config false;
                  description
                    "Out-label.";
                }
                leaf pmsiString {
                  type string {
                    length "1..300";
                  }
                  config false;
                  description
                    "PMSI attribute.";
                }
                leaf attrString {
                  type string {
                    length "1..150";
                  }
                  config false;
                  description
                    "Pravite attribute.";
                }
              }
            }
            container l2vpnAdVpwsRoutingTables {
              config false;
              description
                "List of displayed BGP L2VPN-AD Vpws route information.";
              list l2vpnAdVpwsRoutingTable {
                when "not(../../afType='rpd' or ../../afType='vpnv4flow' or ../../afType='vpnv6flow')";
                key "routeTypeFlag imTableId rd from";
                config false;
                description
                  "Information about BGP L2VPN-AD Vpws routes.";
                leaf l2vpnAdNlri {
                  type string {
                    length "1..50";
                  }
                  config false;
                  description
                    "Prefix of a BGP route.";
                }
                leaf routeTypeFlag {
                  type pub-type:bits32;
                  config false;
                  description
                    "Route type.";
                  ext:masklen 32;
                    ext:bit "ibgp" {
                      position 0;
                    }
                    ext:bit "ebgp" {
                      position 1;
                    }
                    ext:bit "network" {
                      position 2;
                    }
                    ext:bit "import" {
                      position 3;
                    }
                    ext:bit "auto-summary" {
                      position 4;
                    }
                    ext:bit "aggregate" {
                      position 5;
                    }
                    ext:bit "cpri" {
                      position 6;
                    }
                    ext:bit "pcri" {
                      position 7;
                    }
                    ext:bit "suppressed" {
                      position 8;
                    }
                    ext:bit "NHP-EMPTY" {
                      position 9;
                    }
                    ext:bit "NO-ADV" {
                      position 10;
                    }
                    ext:bit "local_cross" {
                      position 11;
                    }
                    ext:bit "remote_cross" {
                      position 12;
                    }
                    ext:bit "VD-BGP" {
                      position 13;
                    }
                    ext:bit "PATH_LOCAL" {
                      position 14;
                    }
                    ext:bit "PATH_GATEWAY" {
                      position 15;
                    }
                    ext:bit "policy_nopass" {
                      position 16;
                    }
                    ext:bit "supprenet" {
                      position 17;
                    }
                    ext:bit "dampened" {
                      position 18;
                    }
                    ext:bit "history" {
                      position 19;
                    }
                    ext:bit "select" {
                      position 20;
                    }
                    ext:bit "best" {
                      position 21;
                    }
                    ext:bit "backup" {
                      position 22;
                    }
                    ext:bit "attr_change" {
                      position 23;
                    }
                    ext:bit "NHLFE_CREATED" {
                      position 24;
                    }
                    ext:bit "ILM_CREATED" {
                      position 25;
                    }
                    ext:bit "NEXTHOP_CHANGE" {
                      position 26;
                    }
                    ext:bit "Invaild" {
                      position 27;
                    }
                    ext:bit "SOURCE_CHANGE" {
                      position 28;
                    }
                    ext:bit "IN_SELECTEDQ" {
                      position 29;
                    }
                    ext:bit "EXITIF_ERROR" {
                      position 30;
                    }
                    ext:bit "GROUP_HEAD" {
                      position 31;
                    }
                }
                leaf imTableId {
                  type uint32 {
                    range "0..4294967295";
                  }
                  config false;
                  description
                    "ID of the routing table to which routes are imported.";
                }
                leaf nexthop {
                  type inet:ip-address-no-zone;
                  config false;
                  description
                    "Next hop address to which packets are forwarded.";
                }
                leaf locPrf {
                  type uint32 {
                    range "0..4294967295";
                  }
                  config false;
                  description
                    "Local-preference.";
                }
                leaf prefVal {
                  type uint32 {
                    range "0..4294967295";
                  }
                  config false;
                  description
                    "Preferred value of a protocol.";
                }
                leaf prefrence {
                  type uint8 {
                    range "0..255";
                  }
                  config false;
                  description
                    "Priority of BGP routes.";
                }
                leaf pathAs {
                  type string {
                    length "1..300";
                  }
                  config false;
                  description
                    "List of the AS_Paths that packets pass through.";
                }
                leaf origin {
                  type bgpcommOrigin;
                  config false;
                  description
                    "Route origin.";
                }
                leaf med {
                  type uint32 {
                    range "0..4294967295";
                  }
                  config false;
                  description
                    "Route MED.";
                }
                leaf flagString {
                  type string {
                    length "1..100";
                  }
                  config false;
                  description
                    "Route flag that contains a string of characters.";
                }
                leaf rd {
                  type string {
                    length "1..22";
                  }
                  config false;
                  description
                    "Route distinguisher.";
                }
                leaf rtWorseReason {
                  type string {
                    length "1..50";
                  }
                  config false;
                  description
                    "Reason why a route is not selected.";
                }
                leaf peerString {
                  type string {
                    length "1..300";
                  }
                  config false;
                  description
                    "List of route sending peers.";
                }
                leaf time {
                  type uint32 {
                    range "0..4294967295";
                  }
                  config false;
                  description
                    "Time stamp of a route.";
                }
                leaf community {
                  type string {
                    length "1..120";
                  }
                  config false;
                  description
                    "Community attribute.";
                }
                leaf extCommunity {
                  type string {
                    length "1..300";
                  }
                  config false;
                  description
                    "Extended community attribute.";
                }
                leaf from {
                  type inet:ip-address-no-zone;
                  config false;
                  description
                    "Source peer that sends a route.";
                }
                leaf ifName {
                  type pub-type:ifName;
                  config false;
                  description
                    "Name of the outbound interface of a route.";
                }
                leaf originator {
                  type inet:ip-address-no-zone;
                  config false;
                  description
                    "Router ID of the route initiator.";
                }
                leaf clusterList {
                  type string {
                    length "1..300";
                  }
                  config false;
                  description
                    "List of cluster IDs.";
                }
                leaf remoteRouteId {
                  type inet:ipv4-address-no-zone;
                  config false;
                  description
                    "Router ID of a peer.";
                }
                leaf relayNexthop {
                  type inet:ip-address-no-zone;
                  config false;
                  description
                    "Next hop to which a route is iterated.";
                }
                leaf relaytnlName {
                  type string {
                    length "1..64";
                  }
                  config false;
                  description
                    "Name of a tunnel to which a route is iterated.";
                }
                leaf inLabel {
                  type uint32 {
                    range "0..4294967295";
                  }
                  config false;
                  description
                    "In-label.";
                }
                leaf outLabel {
                  type uint32 {
                    range "0..4294967295";
                  }
                  config false;
                  description
                    "Out-label.";
                }
                leaf pmsiString {
                  type string {
                    length "1..300";
                  }
                  config false;
                  description
                    "PMSI attribute.";
                }
                leaf attrString {
                  type string {
                    length "1..150";
                  }
                  config false;
                  description
                    "Pravite attribute.";
                }
              }
            }
            container interfaceEsiInfos {
              when "not(../afType='ipv4vpnmcast' or ../afType='mdt' or ../afType='vpntarget' or ../afType='vpnv4flow' or ../afType='vpnv6flow')";
              config false;
              description
                "ESI list.";
              list interfaceEsiInfo {
                when "not(../../afType='rpd') or ../../afType='evpn'";
                key "effectEsi";
                config false;
                description
                  "ESI.";
                leaf effectEsi {
                  type string {
                    length "1..60";
                  }
                  config false;
                  description
                    "Effective ESI.";
                }
                leaf dyminalEsi {
                  type string {
                    length "1..60";
                  }
                  config false;
                  description
                    "Dynamic ESI.";
                }
                leaf staticEsi {
                  type string {
                    length "1..60";
                  }
                  config false;
                  description
                    "Static ESI.";
                }
                container ifLists {
                  config false;
                  description
                    "Interface information list.";
                  list ifList {
                    key "ifName";
                    config false;
                    description
                      "Interface information.";
                    leaf ifName {
                      type pub-type:ifName;
                      config false;
                      description
                        "Interface Name.";
                    }
                  }
                }
              }
            }
            container ipPrefixRoutingTables {
              config false;
              description
                "List of Prefix routes in the EVPN address family.";
              list ipPrefixRoutingTable {
                when "../../afType='evpn'";
                key "rd ipPrefix routeTypeFlag";
                config false;
                description
                  "Prefix route.";
                leaf rd {
                  type string {
                    length "1..60";
                  }
                  config false;
                  description
                    "Route distinguisher. An RD is in the format of 32-bit IP address:16-bit user-defined number, for example, 192.168.122.15:1. The IP address ranges from 0.0.0.0 to 255.255.255.255, and the user-defined number ranges from 0 to 65536. An EVN address family takes effect only after it is configured with a RD.";
                }
                leaf ipPrefix {
                  type string {
                    length "1..60";
                  }
                  config false;
                  description
                    "Prefix route prefix.";
                }
                leaf routeTypeFlag {
                  type pub-type:bits32;
                  config false;
                  description
                    "Route type.";
                  ext:masklen 32;
                    ext:bit "ibgp" {
                      position 0;
                    }
                    ext:bit "ebgp" {
                      position 1;
                    }
                    ext:bit "network" {
                      position 2;
                    }
                    ext:bit "import" {
                      position 3;
                    }
                    ext:bit "auto-summary" {
                      position 4;
                    }
                    ext:bit "aggregate" {
                      position 5;
                    }
                    ext:bit "cpri" {
                      position 6;
                    }
                    ext:bit "pcri" {
                      position 7;
                    }
                    ext:bit "suppressed" {
                      position 8;
                    }
                    ext:bit "NHP-EMPTY" {
                      position 9;
                    }
                    ext:bit "NO-ADV" {
                      position 10;
                    }
                    ext:bit "local_cross" {
                      position 11;
                    }
                    ext:bit "remote_cross" {
                      position 12;
                    }
                    ext:bit "VD-BGP" {
                      position 13;
                    }
                    ext:bit "PATH_LOCAL" {
                      position 14;
                    }
                    ext:bit "PATH_GATEWAY" {
                      position 15;
                    }
                    ext:bit "policy_nopass" {
                      position 16;
                    }
                    ext:bit "supprenet" {
                      position 17;
                    }
                    ext:bit "dampened" {
                      position 18;
                    }
                    ext:bit "history" {
                      position 19;
                    }
                    ext:bit "select" {
                      position 20;
                    }
                    ext:bit "best" {
                      position 21;
                    }
                    ext:bit "backup" {
                      position 22;
                    }
                    ext:bit "attr_change" {
                      position 23;
                    }
                    ext:bit "NHLFE_CREATED" {
                      position 24;
                    }
                    ext:bit "ILM_CREATED" {
                      position 25;
                    }
                    ext:bit "NEXTHOP_CHANGE" {
                      position 26;
                    }
                    ext:bit "Invaild" {
                      position 27;
                    }
                    ext:bit "SOURCE_CHANGE" {
                      position 28;
                    }
                    ext:bit "IN_SELECTEDQ" {
                      position 29;
                    }
                    ext:bit "EXITIF_ERROR" {
                      position 30;
                    }
                    ext:bit "GROUP_HEAD" {
                      position 31;
                    }
                }
                leaf nexthop {
                  type inet:ip-address-no-zone;
                  config false;
                  description
                    "Next-hop address to which packets are sent.";
                }
                leaf locPrf {
                  type uint32 {
                    range "0..4294967295";
                  }
                  config false;
                  description
                    "Local priority.";
                }
                leaf prefVal {
                  type uint32 {
                    range "0..4294967295";
                  }
                  config false;
                  description
                    "Preferred value of a protocol.";
                }
                leaf prefrence {
                  type uint8 {
                    range "0..255";
                  }
                  config false;
                  description
                    "Preference of a route.";
                }
                leaf pathAs {
                  type string {
                    length "1..300";
                  }
                  config false;
                  description
                    "List of the ASs that packets pass through.";
                }
                leaf origin {
                  type bgpcommOrigin;
                  config false;
                  description
                    "Origin of a route.";
                }
                leaf med {
                  type uint32 {
                    range "0..4294967295";
                  }
                  config false;
                  description
                    "Route MED.";
                }
                leaf flagString {
                  type string {
                    length "1..100";
                  }
                  config false;
                  description
                    "Route flag in the format of a character string.";
                }
                leaf peerString {
                  type string {
                    length "1..300";
                  }
                  config false;
                  description
                    "List of sending peers.";
                }
                leaf time {
                  type uint32 {
                    range "0..4294967295";
                  }
                  config false;
                  description
                    "Time stamp of a route.";
                }
                leaf extCommunity {
                  type string {
                    length "1..300";
                  }
                  config false;
                  description
                    "Extended community attribute.";
                }
                leaf rtWorseReason {
                  type string {
                    length "1..50";
                  }
                  config false;
                  description
                    "Reason why a route is not selected.";
                }
                leaf from {
                  type inet:ip-address-no-zone;
                  config false;
                  description
                    "Source peer that sends a route.";
                }
                leaf ifName {
                  type string {
                    length "1..63";
                  }
                  config false;
                  description
                    "Name of the outbound interface of a route.";
                }
                leaf originator {
                  type inet:ipv4-address-no-zone;
                  config false;
                  description
                    "Router ID of the route initiator.";
                }
                leaf remoteRouteId {
                  type inet:ipv4-address-no-zone;
                  config false;
                  description
                    "Router ID of a peer.";
                }
                leaf relayNexthop {
                  type inet:ip-address-no-zone;
                  config false;
                  description
                    "Iterated next hop.";
                }
                leaf relaytnlName {
                  type string {
                    length "1..64";
                  }
                  config false;
                  description
                    "Name of an iteration tunnel.";
                }
                leaf inLabel {
                  type uint32 {
                    range "0..4294967295";
                  }
                  config false;
                  description
                    "In-label.";
                }
                leaf outLabel {
                  type uint32 {
                    range "0..4294967295";
                  }
                  config false;
                  description
                    "Out-label.";
                }
                leaf pmsiString {
                  type string {
                    length "1..300";
                  }
                  config false;
                  description
                    "PMSI attribute.";
                }
                leaf mplsLabel1 {
                  type uint32 {
                    range "0..4294967295";
                  }
                  config false;
                  description
                    "Label1,it means L2 VNI for MAC Route and L3 VNI for Prefix Route.";
                }
                leaf mplsLabel2 {
                  type uint32 {
                    range "0..4294967295";
                  }
                  config false;
                  description
                    "Label2,it means L3 VNI for MAC Route.";
                }
                leaf attrString {
                  type string {
                    length "1..300";
                  }
                  config false;
                  description
                    "Other attribute.";
                }
                leaf community {
                  type string {
                    length "1..120";
                  }
                  config false;
                  description
                    "Community attribute.";
                }
                leaf clusterList {
                  type string {
                    length "1..300";
                  }
                  config false;
                  description
                    "List of cluster IDs.";
                }
              }
            }
            container macRoutingTables {
              when "not(../afType='ipv4vpnmcast' or ../afType='mdt' or ../afType='vpntarget' or ../afType='vpnv4flow' or ../afType='vpnv6flow')";
              config false;
              description
                "List of MAC routes in the EVPN address family.";
              list macRoutingTable {
                when "../../afType='evpn'";
                key "rd macPrefix routeTypeFlag";
                config false;
                description
                  "MAC route.";
                leaf rd {
                  type string {
                    length "1..60";
                  }
                  config false;
                  description
                    "Route distinguisher. An RD is in the format of 32-bit IP address:16-bit user-defined number, for example, 192.168.122.15:1. The IP address ranges from 0.0.0.0 to 255.255.255.255, and the user-defined number ranges from 0 to 65536.An EVN address family takes effect only after it is configured with a RD.";
                }
                leaf macPrefix {
                  type string {
                    length "1..60";
                  }
                  config false;
                  description
                    "MAC route prefix.";
                }
                leaf routeTypeFlag {
                  type pub-type:bits32;
                  config false;
                  description
                    "Route type.";
                  ext:masklen 32;
                    ext:bit "ibgp" {
                      position 0;
                    }
                    ext:bit "ebgp" {
                      position 1;
                    }
                    ext:bit "network" {
                      position 2;
                    }
                    ext:bit "import" {
                      position 3;
                    }
                    ext:bit "auto-summary" {
                      position 4;
                    }
                    ext:bit "aggregate" {
                      position 5;
                    }
                    ext:bit "cpri" {
                      position 6;
                    }
                    ext:bit "pcri" {
                      position 7;
                    }
                    ext:bit "suppressed" {
                      position 8;
                    }
                    ext:bit "NHP-EMPTY" {
                      position 9;
                    }
                    ext:bit "NO-ADV" {
                      position 10;
                    }
                    ext:bit "local_cross" {
                      position 11;
                    }
                    ext:bit "remote_cross" {
                      position 12;
                    }
                    ext:bit "VD-BGP" {
                      position 13;
                    }
                    ext:bit "PATH_LOCAL" {
                      position 14;
                    }
                    ext:bit "PATH_GATEWAY" {
                      position 15;
                    }
                    ext:bit "policy_nopass" {
                      position 16;
                    }
                    ext:bit "supprenet" {
                      position 17;
                    }
                    ext:bit "dampened" {
                      position 18;
                    }
                    ext:bit "history" {
                      position 19;
                    }
                    ext:bit "select" {
                      position 20;
                    }
                    ext:bit "best" {
                      position 21;
                    }
                    ext:bit "backup" {
                      position 22;
                    }
                    ext:bit "attr_change" {
                      position 23;
                    }
                    ext:bit "NHLFE_CREATED" {
                      position 24;
                    }
                    ext:bit "ILM_CREATED" {
                      position 25;
                    }
                    ext:bit "NEXTHOP_CHANGE" {
                      position 26;
                    }
                    ext:bit "Invaild" {
                      position 27;
                    }
                    ext:bit "SOURCE_CHANGE" {
                      position 28;
                    }
                    ext:bit "IN_SELECTEDQ" {
                      position 29;
                    }
                    ext:bit "EXITIF_ERROR" {
                      position 30;
                    }
                    ext:bit "GROUP_HEAD" {
                      position 31;
                    }
                }
                leaf nexthop {
                  type inet:ip-address-no-zone;
                  config false;
                  description
                    "Next-hop address to which packets are sent.";
                }
                leaf locPrf {
                  type uint32 {
                    range "0..4294967295";
                  }
                  config false;
                  description
                    "Local priority.The attribute is only fit for the routes from IBGP peer, not suit for which of EBGP peer.";
                }
                leaf sourceAFI {
                  type bgpcommPrefixType;
                  config false;
                  description
                    "Source address Family.";
                }
                leaf sourceRD {
                  type string {
                    length "3..21";
                  }
                  config false;
                  description
                    "Source RD.";
                }
                leaf prefVal {
                  type uint32 {
                    range "0..4294967295";
                  }
                  config false;
                  description
                    "Preferred value of a protocol.";
                }
                leaf prefrence {
                  type uint8 {
                    range "0..255";
                  }
                  config false;
                  description
                    "Preference of a route.";
                }
                leaf pathAs {
                  type string {
                    length "1..300";
                  }
                  config false;
                  description
                    "List of the ASs that packets pass through.";
                }
                leaf origin {
                  type bgpcommOrigin;
                  config false;
                  description
                    "Origin of a route.";
                }
                leaf med {
                  type uint32 {
                    range "0..4294967295";
                  }
                  config false;
                  description
                    "Route MED.";
                }
                leaf flagString {
                  type string {
                    length "1..100";
                  }
                  config false;
                  description
                    "Route flag in the format of a character string.";
                }
                leaf peerString {
                  type string {
                    length "1..300";
                  }
                  config false;
                  description
                    "List of sending peers.";
                }
                leaf time {
                  type uint32 {
                    range "0..4294967295";
                  }
                  config false;
                  description
                    "Time stamp of a route.";
                }
                leaf extCommunity {
                  type string {
                    length "1..300";
                  }
                  config false;
                  description
                    "Extended community attribute.";
                }
                leaf rtWorseReason {
                  type string {
                    length "1..50";
                  }
                  config false;
                  description
                    "Reason why a route is not selected.";
                }
                leaf from {
                  type inet:ip-address-no-zone;
                  config false;
                  description
                    "Source peer that sends a route.";
                }
                leaf ifName {
                  type string {
                    length "1..63";
                  }
                  config false;
                  description
                    "Name of the outbound interface of a route.";
                }
                leaf originator {
                  type inet:ipv4-address-no-zone;
                  config false;
                  description
                    "Router ID of the route initiator.";
                }
                leaf remoteRouteId {
                  type inet:ipv4-address-no-zone;
                  config false;
                  description
                    "Router ID of a peer.";
                }
                leaf relayNexthop {
                  type inet:ip-address-no-zone;
                  config false;
                  description
                    "Iterated next hop.";
                }
                leaf relaytnlName {
                  type string {
                    length "1..64";
                  }
                  config false;
                  description
                    "Name of an iteration tunnel.";
                }
                leaf inLabel {
                  type uint32 {
                    range "0..4294967295";
                  }
                  config false;
                  description
                    "In-label.";
                }
                leaf outLabel {
                  type uint32 {
                    range "0..4294967295";
                  }
                  config false;
                  description
                    "Out-label.";
                }
                leaf pmsiString {
                  type string {
                    length "1..300";
                  }
                  config false;
                  description
                    "PMSI attribute.";
                }
                leaf mplsLabel1 {
                  type uint32 {
                    range "0..4294967295";
                  }
                  config false;
                  description
                    "Label1,it means L2 VNI for MAC Route and L3 VNI for Prefix Route.";
                }
                leaf mplsLabel2 {
                  type uint32 {
                    range "0..4294967295";
                  }
                  config false;
                  description
                    "Label2,it means L3 VNI for MAC Route.";
                }
                leaf attrString {
                  type string {
                    length "1..300";
                  }
                  config false;
                  description
                    "Other attribute.";
                }
                leaf community {
                  type string {
                    length "1..120";
                  }
                  config false;
                  description
                    "Community attribute.";
                }
                leaf clusterList {
                  type string {
                    length "1..300";
                  }
                  config false;
                  description
                    "List of cluster IDs.";
                }
                leaf frrOutIfName {
                  type string {
                    length "1..64";
                  }
                  config false;
                  description
                    "Local-Remote Frr Direct Out-interface.";
                }
                leaf frrNexthop {
                  type inet:ipv4-address-no-zone;
                  config false;
                  description
                    "Local-Remote Frr Nexthop.";
                }
                leaf frrTnlOutIf {
                  type string {
                    length "1..64";
                  }
                  config false;
                  description
                    "Local-Remote Frr Tunnel Out-Interface.";
                }
                leaf effectNexthop {
                  type inet:ip-address-no-zone;
                  config false;
                  description
                    "Effective nexthop.";
                }
                leaf redirectOutIf {
                  type string {
                    length "1..64";
                  }
                  config false;
                  description
                    "Redirect Out-Interface.";
                }
              }
            }
            container esRoutingTables {
              when "not(../afType='ipv4vpnmcast' or ../afType='mdt' or ../afType='vpntarget' or ../afType='vpnv4flow' or ../afType='vpnv6flow')";
              config false;
              description
                "List of ES routes in the EVN address family.";
              list esRoutingTable {
                when "not(../../afType='rpd') or ../../afType='evpn'";
                key "rd esPrefix routeTypeFlag";
                config false;
                description
                  "ES route in the EVN address family.";
                leaf rd {
                  type string {
                    length "1..60";
                  }
                  config false;
                  description
                    "Route distinguisher. An RD is in the format of 32-bit IP address:16-bit user-defined number, for example, 192.168.122.15:1. The IP address ranges from 0.0.0.0 to 255.255.255.255, and the user-defined number ranges from 0 to 65536. An EVN address family takes effect only after it is configured with a RD.";
                }
                leaf esPrefix {
                  type string {
                    length "1..60";
                  }
                  config false;
                  description
                    "ES route prefix.";
                }
                leaf routeTypeFlag {
                  type pub-type:bits32;
                  config false;
                  description
                    "Route type.";
                  ext:masklen 32;
                    ext:bit "ibgp" {
                      position 0;
                    }
                    ext:bit "ebgp" {
                      position 1;
                    }
                    ext:bit "network" {
                      position 2;
                    }
                    ext:bit "import" {
                      position 3;
                    }
                    ext:bit "auto-summary" {
                      position 4;
                    }
                    ext:bit "aggregate" {
                      position 5;
                    }
                    ext:bit "cpri" {
                      position 6;
                    }
                    ext:bit "pcri" {
                      position 7;
                    }
                    ext:bit "suppressed" {
                      position 8;
                    }
                    ext:bit "NHP-EMPTY" {
                      position 9;
                    }
                    ext:bit "NO-ADV" {
                      position 10;
                    }
                    ext:bit "local_cross" {
                      position 11;
                    }
                    ext:bit "remote_cross" {
                      position 12;
                    }
                    ext:bit "VD-BGP" {
                      position 13;
                    }
                    ext:bit "PATH_LOCAL" {
                      position 14;
                    }
                    ext:bit "PATH_GATEWAY" {
                      position 15;
                    }
                    ext:bit "policy_nopass" {
                      position 16;
                    }
                    ext:bit "supprenet" {
                      position 17;
                    }
                    ext:bit "dampened" {
                      position 18;
                    }
                    ext:bit "history" {
                      position 19;
                    }
                    ext:bit "select" {
                      position 20;
                    }
                    ext:bit "best" {
                      position 21;
                    }
                    ext:bit "backup" {
                      position 22;
                    }
                    ext:bit "attr_change" {
                      position 23;
                    }
                    ext:bit "NHLFE_CREATED" {
                      position 24;
                    }
                    ext:bit "ILM_CREATED" {
                      position 25;
                    }
                    ext:bit "NEXTHOP_CHANGE" {
                      position 26;
                    }
                    ext:bit "Invaild" {
                      position 27;
                    }
                    ext:bit "SOURCE_CHANGE" {
                      position 28;
                    }
                    ext:bit "IN_SELECTEDQ" {
                      position 29;
                    }
                    ext:bit "EXITIF_ERROR" {
                      position 30;
                    }
                    ext:bit "GROUP_HEAD" {
                      position 31;
                    }
                }
                leaf nexthop {
                  type inet:ip-address-no-zone;
                  config false;
                  description
                    "Next-hop address to which packets are sent.";
                }
                leaf locPrf {
                  type uint32 {
                    range "0..4294967295";
                  }
                  config false;
                  description
                    "Local priority.";
                }
                leaf prefVal {
                  type uint32 {
                    range "0..4294967295";
                  }
                  config false;
                  description
                    "Preferred value of a protocol.";
                }
                leaf prefrence {
                  type uint8 {
                    range "0..255";
                  }
                  config false;
                  description
                    "Rreference of a route.";
                }
                leaf pathAs {
                  type string {
                    length "1..300";
                  }
                  config false;
                  description
                    "List of the ASs that packets pass through.";
                }
                leaf origin {
                  type bgpcommOrigin;
                  config false;
                  description
                    "Origin of a route.";
                }
                leaf med {
                  type uint32 {
                    range "0..4294967295";
                  }
                  config false;
                  description
                    "Route MED.";
                }
                leaf flagString {
                  type string {
                    length "1..100";
                  }
                  config false;
                  description
                    "Route flag that contains a string of characters.";
                }
                leaf rtWorseReason {
                  type string {
                    length "1..50";
                  }
                  config false;
                  description
                    "Reason why a route is not selected.";
                }
                leaf peerString {
                  type string {
                    length "1..300";
                  }
                  config false;
                  description
                    "List of sending peers.";
                }
                leaf time {
                  type uint32 {
                    range "0..4294967295";
                  }
                  config false;
                  description
                    "Time stamp of a route.";
                }
                leaf extCommunity {
                  type string {
                    length "1..300";
                  }
                  config false;
                  description
                    "Extended community attribute.";
                }
                leaf from {
                  type inet:ip-address-no-zone;
                  config false;
                  description
                    "Source peer that sends a route.";
                }
                leaf ifName {
                  type string {
                    length "1..63";
                  }
                  config false;
                  description
                    "Name of the outbound interface of a route.";
                }
                leaf originator {
                  type inet:ipv4-address-no-zone;
                  config false;
                  description
                    "Router ID of the route initiator.";
                }
                leaf remoteRouteId {
                  type inet:ipv4-address-no-zone;
                  config false;
                  description
                    "Router ID of a peer.";
                }
                leaf relayNexthop {
                  type inet:ip-address-no-zone;
                  config false;
                  description
                    "Iterated next hop.";
                }
                leaf relaytnlName {
                  type string {
                    length "1..64";
                  }
                  config false;
                  description
                    "Name of an iteration tunnel.";
                }
                leaf inLabel {
                  type uint32 {
                    range "0..4294967295";
                  }
                  config false;
                  description
                    "In-label.";
                }
                leaf outLabel {
                  type uint32 {
                    range "0..4294967295";
                  }
                  config false;
                  description
                    "Out-label.";
                }
                leaf pmsiString {
                  type string {
                    length "1..300";
                  }
                  config false;
                  description
                    "PMSI attribute.";
                }
                leaf attrString {
                  type string {
                    length "1..300";
                  }
                  config false;
                  description
                    "Other attribute.";
                }
                leaf community {
                  type string {
                    length "1..120";
                  }
                  config false;
                  description
                    "Community attribute.";
                }
                leaf clusterList {
                  type string {
                    length "1..300";
                  }
                  config false;
                  description
                    "List of cluster IDs.";
                }
              }
            }
            container multiRoutingTables {
              when "not(../afType='ipv4vpnmcast' or ../afType='mdt' or ../afType='vpntarget' or ../afType='vpnv4flow' or ../afType='vpnv6flow')";
              config false;
              description
                "List of inclusive routes information in the EVPN address family.";
              list multiRoutingTable {
                when "not(../../afType='rpd') or ../../afType='evpn'";
                key "rd inclusivePrefix routeTypeFlag";
                config false;
                description
                  "Inclusive route in the EVPN address family.";
                leaf rd {
                  type string {
                    length "1..60";
                  }
                  config false;
                  description
                    "Route distinguisher. An EVN address family takes effect only after it is configured with a RD. The format of an RD is as follows:32-bit IP address:16-bit user-defined number, for example: 192.168.122.15:1.The IP address ranges from 0.0.0.0 to 255.255.255.255, and the user-defined number ranges from 0 to 65536.";
                }
                leaf inclusivePrefix {
                  type inet:ipv4-address-no-zone;
                  config false;
                  description
                    "Inclusive route prefix.";
                }
                leaf routeTypeFlag {
                  type pub-type:bits32;
                  config false;
                  description
                    "Route type.";
                  ext:masklen 32;
                    ext:bit "ibgp" {
                      position 0;
                    }
                    ext:bit "ebgp" {
                      position 1;
                    }
                    ext:bit "network" {
                      position 2;
                    }
                    ext:bit "import" {
                      position 3;
                    }
                    ext:bit "auto-summary" {
                      position 4;
                    }
                    ext:bit "aggregate" {
                      position 5;
                    }
                    ext:bit "cpri" {
                      position 6;
                    }
                    ext:bit "pcri" {
                      position 7;
                    }
                    ext:bit "suppressed" {
                      position 8;
                    }
                    ext:bit "NHP-EMPTY" {
                      position 9;
                    }
                    ext:bit "NO-ADV" {
                      position 10;
                    }
                    ext:bit "local_cross" {
                      position 11;
                    }
                    ext:bit "remote_cross" {
                      position 12;
                    }
                    ext:bit "VD-BGP" {
                      position 13;
                    }
                    ext:bit "PATH_LOCAL" {
                      position 14;
                    }
                    ext:bit "PATH_GATEWAY" {
                      position 15;
                    }
                    ext:bit "policy_nopass" {
                      position 16;
                    }
                    ext:bit "supprenet" {
                      position 17;
                    }
                    ext:bit "dampened" {
                      position 18;
                    }
                    ext:bit "history" {
                      position 19;
                    }
                    ext:bit "select" {
                      position 20;
                    }
                    ext:bit "best" {
                      position 21;
                    }
                    ext:bit "backup" {
                      position 22;
                    }
                    ext:bit "attr_change" {
                      position 23;
                    }
                    ext:bit "NHLFE_CREATED" {
                      position 24;
                    }
                    ext:bit "ILM_CREATED" {
                      position 25;
                    }
                    ext:bit "NEXTHOP_CHANGE" {
                      position 26;
                    }
                    ext:bit "Invaild" {
                      position 27;
                    }
                    ext:bit "SOURCE_CHANGE" {
                      position 28;
                    }
                    ext:bit "IN_SELECTEDQ" {
                      position 29;
                    }
                    ext:bit "EXITIF_ERROR" {
                      position 30;
                    }
                    ext:bit "GROUP_HEAD" {
                      position 31;
                    }
                }
                leaf nexthop {
                  type inet:ip-address-no-zone;
                  config false;
                  description
                    "Next-hop address to which packets are sent.";
                }
                leaf locPrf {
                  type uint32 {
                    range "0..4294967295";
                  }
                  config false;
                  description
                    "Local priority.";
                }
                leaf prefVal {
                  type uint32 {
                    range "0..4294967295";
                  }
                  config false;
                  description
                    "Preferred value of a protocol.";
                }
                leaf prefrence {
                  type uint8 {
                    range "0..255";
                  }
                  config false;
                  description
                    "Preference of a route.";
                }
                leaf pathAs {
                  type string {
                    length "1..300";
                  }
                  config false;
                  description
                    "List of the ASs that packets pass through.";
                }
                leaf origin {
                  type bgpcommOrigin;
                  config false;
                  description
                    "Origin of a route.";
                }
                leaf med {
                  type uint32 {
                    range "0..4294967295";
                  }
                  config false;
                  description
                    "Route MED in the attribute node.";
                }
                leaf flagString {
                  type string {
                    length "1..100";
                  }
                  config false;
                  description
                    "Route flag in the format of a character string.";
                }
                leaf rtWorseReason {
                  type string {
                    length "1..50";
                  }
                  config false;
                  description
                    "Reason why a route is not selected.";
                }
                leaf peerString {
                  type string {
                    length "1..300";
                  }
                  config false;
                  description
                    "List of sending peers.";
                }
                leaf time {
                  type uint32 {
                    range "0..4294967295";
                  }
                  config false;
                  description
                    "Time stamp of a route.";
                }
                leaf extCommunity {
                  type string {
                    length "1..300";
                  }
                  config false;
                  description
                    "Extended community attribute.";
                }
                leaf from {
                  type inet:ip-address-no-zone;
                  config false;
                  description
                    "Source peer that sends a route.";
                }
                leaf ifName {
                  type string {
                    length "1..63";
                  }
                  config false;
                  description
                    "Name of the outbound interface of a route.";
                }
                leaf originator {
                  type inet:ipv4-address-no-zone;
                  config false;
                  description
                    "Router ID of the route initiator.";
                }
                leaf remoteRouteId {
                  type inet:ipv4-address-no-zone;
                  config false;
                  description
                    "Router ID of a peer.";
                }
                leaf relayNexthop {
                  type inet:ip-address-no-zone;
                  config false;
                  description
                    "Iterated next hop.";
                }
                leaf relaytnlName {
                  type string {
                    length "1..64";
                  }
                  config false;
                  description
                    "Name of an iteration tunnel.";
                }
                leaf inLabel {
                  type uint32 {
                    range "0..4294967295";
                  }
                  config false;
                  description
                    "In-label.";
                }
                leaf outLabel {
                  type uint32 {
                    range "0..4294967295";
                  }
                  config false;
                  description
                    "Out-label.";
                }
                leaf pmsiString {
                  type string {
                    length "1..300";
                  }
                  config false;
                  description
                    "PMSI attribute.";
                }
                leaf attrString {
                  type string {
                    length "1..300";
                  }
                  config false;
                  description
                    "Other attribute.";
                }
                leaf community {
                  type string {
                    length "1..120";
                  }
                  config false;
                  description
                    "Community attribute.";
                }
                leaf clusterList {
                  type string {
                    length "1..300";
                  }
                  config false;
                  description
                    "List of cluster IDs.";
                }
              }
            }
            container vpnv4McastRoutingTables {
              when "not(../afType='evpn') or ../afType='ipv4vpnmcast'";
              config false;
              description
                "List of displayed route information in VPNv4 Multicast address family.";
              list vpnv4McastRoutingTable {
                when "not(../../afType='evpn' or ../../afType='vpnv4flow')";
                key "from networkPrefix prefixMask rd routeTypeFlag imTableId";
                config false;
                description
                  "Information about VPNv4 Multicast routes.";
                leaf from {
                  type inet:ip-address-no-zone;
                  config false;
                  description
                    "Source peer that sends a route.";
                }
                leaf networkPrefix {
                  type inet:ip-address-no-zone;
                  config false;
                  description
                    "BGP route prefix.";
                }
                leaf prefixMask {
                  type uint8;
                  config false;
                  description
                    "Prefix mask.";
                }
                leaf rd {
                  type string {
                    length "1..60";
                  }
                  config false;
                  description
                    "Route distinguisher.";
                }
                leaf routeTypeFlag {
                  type pub-type:bits32 {
                    ext:masklen 32;
                      ext:bit "ibgp" {
                        position 0;
                      }
                      ext:bit "ebgp" {
                        position 1;
                      }
                      ext:bit "network" {
                        position 2;
                      }
                      ext:bit "import" {
                        position 3;
                      }
                      ext:bit "auto-summary" {
                        position 4;
                      }
                      ext:bit "aggregate" {
                        position 5;
                      }
                      ext:bit "cpri" {
                        position 6;
                      }
                      ext:bit "pcri" {
                        position 7;
                      }
                      ext:bit "suppressed" {
                        position 8;
                      }
                      ext:bit "NHP-EMPTY" {
                        position 9;
                      }
                      ext:bit "NO-ADV" {
                        position 10;
                      }
                      ext:bit "local_cross" {
                        position 11;
                      }
                      ext:bit "remote_cross" {
                        position 12;
                      }
                      ext:bit "VD-BGP" {
                        position 13;
                      }
                      ext:bit "PATH_LOCAL" {
                        position 14;
                      }
                      ext:bit "PATH_GATEWAY" {
                        position 15;
                      }
                      ext:bit "policy_nopass" {
                        position 16;
                      }
                      ext:bit "supprenet" {
                        position 17;
                      }
                      ext:bit "dampened" {
                        position 18;
                      }
                      ext:bit "history" {
                        position 19;
                      }
                      ext:bit "select" {
                        position 20;
                      }
                      ext:bit "best" {
                        position 21;
                      }
                      ext:bit "backup" {
                        position 22;
                      }
                      ext:bit "attr_change" {
                        position 23;
                      }
                      ext:bit "NHLFE_CREATED" {
                        position 24;
                      }
                      ext:bit "ILM_CREATED" {
                        position 25;
                      }
                      ext:bit "NEXTHOP_CHANGE" {
                        position 26;
                      }
                      ext:bit "Invaild" {
                        position 27;
                      }
                      ext:bit "SOURCE_CHANGE" {
                        position 28;
                      }
                      ext:bit "IN_SELECTEDQ" {
                        position 29;
                      }
                      ext:bit "EXITIF_ERROR" {
                        position 30;
                      }
                      ext:bit "GROUP_HEAD" {
                        position 31;
                      }
                  }
                  config false;
                  description
                    "Route type.";
                }
                leaf imTableId {
                  type uint32 {
                    range "0..4294967295";
                  }
                  config false;
                  description
                    "ID of the routing table to which routes are imported.";
                }
                leaf nexthop {
                  type inet:ip-address-no-zone;
                  config false;
                  description
                    "Next hop address to which packets are forwarded.";
                }
                leaf locPrf {
                  type uint32 {
                    range "0..4294967295";
                  }
                  config false;
                  description
                    "Local priority.The attribute is only fit for the routes from IBGP peer, not suit for which of EBGP peer.";
                }
                leaf prefVal {
                  type uint32 {
                    range "0..4294967295";
                  }
                  config false;
                  description
                    "Preferred value of a protocol.";
                }
                leaf prefrence {
                  type uint8 {
                    range "0..255";
                  }
                  config false;
                  description
                    "Priority of BGP routes.";
                }
                leaf pathAs {
                  type string {
                    length "1..300";
                  }
                  config false;
                  description
                    "List of the AS_Paths that packets pass through.";
                }
                leaf origin {
                  type bgpcommOrigin;
                  config false;
                  description
                    "Route origin.";
                }
                leaf med {
                  type uint32 {
                    range "0..4294967295";
                  }
                  config false;
                  description
                    "Route MED.The attribute is only fit for the routes from EBGP peer, not suit for which of IBGP peer.";
                }
                leaf flagString {
                  type string {
                    length "1..100";
                  }
                  config false;
                  description
                    "Route flag that contains a string of characters.";
                }
                leaf rtWorseReason {
                  type string {
                    length "1..50";
                  }
                  config false;
                  description
                    "Reason why a route is not selected.";
                }
                leaf peerString {
                  type string {
                    length "1..300";
                  }
                  config false;
                  description
                    "List of route sending peers.";
                }
                leaf time {
                  type uint32 {
                    range "0..4294967295";
                  }
                  config false;
                  description
                    "Time stamp of a route.";
                }
                leaf community {
                  type string {
                    length "1..300";
                  }
                  config false;
                  description
                    "Community attribute.";
                }
                leaf extCommunity {
                  type string {
                    length "0..300";
                  }
                  config false;
                  description
                    "Extended community attribute.";
                }
                leaf ifName {
                  type pub-type:ifName;
                  config false;
                  description
                    "Name of the outbound interface of a route.";
                }
                leaf originator {
                  type inet:ip-address-no-zone;
                  config false;
                  description
                    "Router ID of the route initiator.";
                }
                leaf clusterList {
                  type string {
                    length "0..300";
                  }
                  config false;
                  description
                    "List of cluster IDs.";
                }
                leaf remoteRouteId {
                  type inet:ipv4-address-no-zone;
                  config false;
                  description
                    "Router ID of a peer.";
                }
                leaf relayNexthop {
                  type inet:ip-address-no-zone;
                  config false;
                  description
                    "Next hop to which a route is iterated.";
                }
                leaf relaytnlName {
                  type string {
                    length "1..64";
                  }
                  config false;
                  description
                    "Name of a tunnel to which a route is iterated.";
                }
                leaf inLabel {
                  type uint32 {
                    range "0..4294967295";
                  }
                  config false;
                  description
                    "In-label.";
                }
                leaf outLabel {
                  type uint32 {
                    range "0..4294967295";
                  }
                  config false;
                  description
                    "Out-label.";
                }
                leaf advNextHop {
                  type inet:ip-address-no-zone;
                  config false;
                  description
                    "Next hop of an BGP.";
                }
              }
            }
            container ipv4MdtRoutingTables {
              when "not(../afType='evpn') or ../afType='mdt'";
              config false;
              description
                "List of displayed route information in MDT address family.";
              list ipv4MdtRoutingTable {
                when "not(../../afType='evpn' or ../../afType='vpnv4flow')";
                key "from networkPrefix prefixMask mdtGroupAddr rd routeTypeFlag imTableId";
                config false;
                description
                  "Information about MDT routes.";
                leaf from {
                  type inet:ip-address-no-zone;
                  config false;
                  description
                    "Source peer that sends a route.";
                }
                leaf networkPrefix {
                  type inet:ip-address-no-zone;
                  config false;
                  description
                    "BGP route prefix.";
                }
                leaf prefixMask {
                  type uint8;
                  config false;
                  description
                    "Prefix mask.";
                }
                leaf mdtGroupAddr {
                  type inet:ip-address-no-zone;
                  config false;
                  description
                    "MDT Group Address.";
                }
                leaf rd {
                  type string {
                    length "1..22";
                  }
                  config false;
                  description
                    "Route distinguisher.";
                }
                leaf routeTypeFlag {
                  type pub-type:bits32 {
                    ext:masklen 32;
                      ext:bit "ibgp" {
                        position 0;
                      }
                      ext:bit "ebgp" {
                        position 1;
                      }
                      ext:bit "network" {
                        position 2;
                      }
                      ext:bit "import" {
                        position 3;
                      }
                      ext:bit "auto-summary" {
                        position 4;
                      }
                      ext:bit "aggregate" {
                        position 5;
                      }
                      ext:bit "cpri" {
                        position 6;
                      }
                      ext:bit "pcri" {
                        position 7;
                      }
                      ext:bit "suppressed" {
                        position 8;
                      }
                      ext:bit "NHP-EMPTY" {
                        position 9;
                      }
                      ext:bit "NO-ADV" {
                        position 10;
                      }
                      ext:bit "local_cross" {
                        position 11;
                      }
                      ext:bit "remote_cross" {
                        position 12;
                      }
                      ext:bit "VD-BGP" {
                        position 13;
                      }
                      ext:bit "PATH_LOCAL" {
                        position 14;
                      }
                      ext:bit "PATH_GATEWAY" {
                        position 15;
                      }
                      ext:bit "policy_nopass" {
                        position 16;
                      }
                      ext:bit "supprenet" {
                        position 17;
                      }
                      ext:bit "dampened" {
                        position 18;
                      }
                      ext:bit "history" {
                        position 19;
                      }
                      ext:bit "select" {
                        position 20;
                      }
                      ext:bit "best" {
                        position 21;
                      }
                      ext:bit "backup" {
                        position 22;
                      }
                      ext:bit "attr_change" {
                        position 23;
                      }
                      ext:bit "NHLFE_CREATED" {
                        position 24;
                      }
                      ext:bit "ILM_CREATED" {
                        position 25;
                      }
                      ext:bit "NEXTHOP_CHANGE" {
                        position 26;
                      }
                      ext:bit "Invaild" {
                        position 27;
                      }
                      ext:bit "SOURCE_CHANGE" {
                        position 28;
                      }
                      ext:bit "IN_SELECTEDQ" {
                        position 29;
                      }
                      ext:bit "EXITIF_ERROR" {
                        position 30;
                      }
                      ext:bit "GROUP_HEAD" {
                        position 31;
                      }
                  }
                  config false;
                  description
                    "Route type.";
                }
                leaf imTableId {
                  type uint32 {
                    range "0..4294967295";
                  }
                  config false;
                  description
                    "ID of the routing table to which routes are imported.";
                }
                leaf nexthop {
                  type inet:ip-address-no-zone;
                  config false;
                  description
                    "Next hop address to which packets are forwarded.";
                }
                leaf locPrf {
                  type uint32 {
                    range "0..4294967295";
                  }
                  config false;
                  description
                    "Local priority.The attribute is only fit for the routes from IBGP peer, not suit for which of EBGP peer.";
                }
                leaf prefVal {
                  type uint32 {
                    range "0..4294967295";
                  }
                  config false;
                  description
                    "Preferred value of a protocol.";
                }
                leaf prefrence {
                  type uint8 {
                    range "0..255";
                  }
                  config false;
                  description
                    "Priority of BGP routes.";
                }
                leaf pathAs {
                  type string {
                    length "1..300";
                  }
                  config false;
                  description
                    "List of the AS_Paths that packets pass through.";
                }
                leaf origin {
                  type bgpcommOrigin;
                  config false;
                  description
                    "Route origin.";
                }
                leaf med {
                  type uint32 {
                    range "0..4294967295";
                  }
                  config false;
                  description
                    "Route MED.The attribute is only fit for the routes from EBGP peer, not suit for which of IBGP peer.";
                }
                leaf flagString {
                  type string {
                    length "1..100";
                  }
                  config false;
                  description
                    "Route flag that contains a string of characters.";
                }
                leaf rtWorseReason {
                  type string {
                    length "1..50";
                  }
                  config false;
                  description
                    "Reason why a route is not selected.";
                }
                leaf peerString {
                  type string {
                    length "1..300";
                  }
                  config false;
                  description
                    "List of route sending peers.";
                }
                leaf time {
                  type uint32 {
                    range "0..4294967295";
                  }
                  config false;
                  description
                    "Time stamp of a route.";
                }
                leaf community {
                  type string {
                    length "1..120";
                  }
                  config false;
                  description
                    "Community attribute.";
                }
                leaf extCommunity {
                  type string {
                    length "1..300";
                  }
                  config false;
                  description
                    "Extended community attribute.";
                }
                leaf ifName {
                  type pub-type:ifName;
                  config false;
                  description
                    "Name of the outbound interface of a route.";
                }
                leaf originator {
                  type inet:ip-address-no-zone;
                  config false;
                  description
                    "Router ID of the route initiator.";
                }
                leaf clusterList {
                  type string {
                    length "1..300";
                  }
                  config false;
                  description
                    "List of cluster IDs.";
                }
                leaf remoteRouteId {
                  type inet:ipv4-address-no-zone;
                  config false;
                  description
                    "Router ID of a peer.";
                }
                leaf relayNexthop {
                  type inet:ip-address-no-zone;
                  config false;
                  description
                    "Next hop to which a route is iterated.";
                }
                leaf relaytnlName {
                  type string {
                    length "1..64";
                  }
                  config false;
                  description
                    "Name of a tunnel to which a route is iterated.";
                }
                leaf inLabel {
                  type uint32 {
                    range "0..4294967295";
                  }
                  config false;
                  description
                    "In-label.";
                }
                leaf outLabel {
                  type uint32 {
                    range "0..4294967295";
                  }
                  config false;
                  description
                    "Out-label.";
                }
                leaf advNextHop {
                  type inet:ip-address-no-zone;
                  config false;
                  description
                    "Next hop of an BGP.";
                }
              }
            }
            container vpnTargetRoutingTables {
              config false;
              description
                "Information about VT routes in the VPN-TARGET address family.";
              list vpnTargetRoutingTable {
                when "not(../../afType='vpnv4flow')";
                key "from routeTypeFlag imTableId rd";
                config false;
                description
                  "Information about VT routes in the VPN-TARGET address family.";
                leaf from {
                  type inet:ip-address-no-zone;
                  config false;
                  description
                    "Source peer that sends a route.";
                }
                leaf routeTypeFlag {
                  type pub-type:bits32 {
                    ext:masklen 32;
                      ext:bit "ibgp" {
                        position 0;
                      }
                      ext:bit "ebgp" {
                        position 1;
                      }
                      ext:bit "network" {
                        position 2;
                      }
                      ext:bit "import" {
                        position 3;
                      }
                      ext:bit "auto-summary" {
                        position 4;
                      }
                      ext:bit "aggregate" {
                        position 5;
                      }
                      ext:bit "cpri" {
                        position 6;
                      }
                      ext:bit "pcri" {
                        position 7;
                      }
                      ext:bit "suppressed" {
                        position 8;
                      }
                      ext:bit "NHP-EMPTY" {
                        position 9;
                      }
                      ext:bit "NO-ADV" {
                        position 10;
                      }
                      ext:bit "local_cross" {
                        position 11;
                      }
                      ext:bit "remote_cross" {
                        position 12;
                      }
                      ext:bit "VD-BGP" {
                        position 13;
                      }
                      ext:bit "PATH_LOCAL" {
                        position 14;
                      }
                      ext:bit "PATH_GATEWAY" {
                        position 15;
                      }
                      ext:bit "policy_nopass" {
                        position 16;
                      }
                      ext:bit "supprenet" {
                        position 17;
                      }
                      ext:bit "dampened" {
                        position 18;
                      }
                      ext:bit "history" {
                        position 19;
                      }
                      ext:bit "select" {
                        position 20;
                      }
                      ext:bit "best" {
                        position 21;
                      }
                      ext:bit "backup" {
                        position 22;
                      }
                      ext:bit "attr_change" {
                        position 23;
                      }
                      ext:bit "NHLFE_CREATED" {
                        position 24;
                      }
                      ext:bit "ILM_CREATED" {
                        position 25;
                      }
                      ext:bit "NEXTHOP_CHANGE" {
                        position 26;
                      }
                      ext:bit "Invaild" {
                        position 27;
                      }
                      ext:bit "SOURCE_CHANGE" {
                        position 28;
                      }
                      ext:bit "IN_SELECTEDQ" {
                        position 29;
                      }
                      ext:bit "EXITIF_ERROR" {
                        position 30;
                      }
                      ext:bit "GROUP_HEAD" {
                        position 31;
                      }
                  }
                  config false;
                  description
                    "Route type.";
                }
                leaf imTableId {
                  type uint32 {
                    range "0..4294967295";
                  }
                  config false;
                  description
                    "ID of the routing table to which routes are imported.";
                }
                leaf rd {
                  type string {
                    length "0..22";
                  }
                  config false;
                  description
                    "Route distinguisher.";
                }
                leaf vtPrefix {
                  type string {
                    length "0..50";
                  }
                  config false;
                  description
                    "Prefix of a BGP route.";
                }
                leaf originAs {
                  type string {
                    length "0..50";
                  }
                  config false;
                  description
                    "Origin-As.";
                }
                leaf nexthop {
                  type inet:ip-address-no-zone;
                  config false;
                  description
                    "Next hop address to which packets are forwarded.";
                }
                leaf locPrf {
                  type uint32 {
                    range "0..4294967295";
                  }
                  config false;
                  description
                    "Local priority.The attribute is only fit for the routes from IBGP peer, not suit for which of EBGP peer.";
                }
                leaf prefVal {
                  type uint32 {
                    range "0..4294967295";
                  }
                  config false;
                  description
                    "Preferred value of a protocol.";
                }
                leaf prefrence {
                  type uint8 {
                    range "0..255";
                  }
                  config false;
                  description
                    "Priority of BGP routes.";
                }
                leaf pathAs {
                  type string {
                    length "1..300";
                  }
                  config false;
                  description
                    "List of the AS_Paths that packets pass through.";
                }
                leaf origin {
                  type bgpcommOrigin;
                  config false;
                  description
                    "Route origin.";
                }
                leaf med {
                  type uint32 {
                    range "0..4294967295";
                  }
                  config false;
                  description
                    "Route MED.The attribute is only fit for the routes from EBGP peer, not suit for which of IBGP peer.";
                }
                leaf flagString {
                  type string {
                    length "1..100";
                  }
                  config false;
                  description
                    "Route flag that contains a string of characters.";
                }
                leaf rtWorseReason {
                  type string {
                    length "1..50";
                  }
                  config false;
                  description
                    "Reason why a route is not selected.";
                }
                leaf peerString {
                  type string {
                    length "1..300";
                  }
                  config false;
                  description
                    "List of route sending peers.";
                }
                leaf time {
                  type uint32 {
                    range "0..4294967295";
                  }
                  config false;
                  description
                    "Time stamp of a route.";
                }
                leaf community {
                  type string {
                    length "1..120";
                  }
                  config false;
                  description
                    "Community attribute.";
                }
                leaf extCommunity {
                  type string {
                    length "1..300";
                  }
                  config false;
                  description
                    "Extended community attribute.";
                }
                leaf ifName {
                  type pub-type:ifName;
                  config false;
                  description
                    "Name of the outbound interface of a route.";
                }
                leaf originator {
                  type inet:ip-address-no-zone;
                  config false;
                  description
                    "Router ID of the route initiator.";
                }
                leaf clusterList {
                  type string {
                    length "1..300";
                  }
                  config false;
                  description
                    "List of cluster IDs.";
                }
                leaf remoteRouteId {
                  type inet:ipv4-address-no-zone;
                  config false;
                  description
                    "Router ID of a peer.";
                }
                leaf relayNexthop {
                  type inet:ip-address-no-zone;
                  config false;
                  description
                    "Next hop to which a route is iterated.";
                }
                leaf relaytnlName {
                  type string {
                    length "1..64";
                  }
                  config false;
                  description
                    "Name of a tunnel to which a route is iterated.";
                }
                leaf inLabel {
                  type uint32 {
                    range "0..4294967295";
                  }
                  config false;
                  description
                    "In-label.";
                }
                leaf outLabel {
                  type uint32 {
                    range "0..4294967295";
                  }
                  config false;
                  description
                    "Out-label.";
                }
                leaf advNextHop {
                  type inet:ip-address-no-zone;
                  config false;
                  description
                    "Next hop of an BGP.";
                }
              }
            }			
            container bgpRtStaticsInfo {
              config false;
              description
                "Display BGP route statics info.";
              leaf rtTotalNum {
                type uint32;
                default "0";
                config false;
                description
                  "Total Number of Routes.";
              }
              leaf advRmTotalNum {
                type uint32;
                config false;
                description
                  "Total Number of Prefix Advertised to RM.";
              }
              leaf activeRtNum {
                type uint32;
                config false;
                description
                  "Total Number of Active Route.";
              }
              leaf bestRtNum {
                type uint32;
                config false;
                description
                  "Total Number of Best Routes.";
              }
              leaf addPathRtNum {
                type uint32;
                config false;
                description
                  "Total Number of Add-path Routes.";
              }
              leaf advBestRtNum {
                type uint32;
                config false;
                description
                  "Total Number of Best-external Routes.";
              }
              leaf cidrRtNum {
                type uint32;
                config false;
                description
                  "Total Number of Cidr Routes.";
              }
              leaf cmmyRtNum {
                type uint32;
                config false;
                description
                  "Total Number of Community Routes.";
              }
              leaf diffOriAsRtNum {
                type uint32;
                config false;
                description
                  "Total Number of Different-origin-as Routes.";
              }
              leaf dampRtNum {
                type uint32;
                config false;
                description
                  "Total Number of Dampened Routes.";
              }
              leaf fromPeRtNum {
                type uint32;
                config false;
                description
                  "Total number of routes from all PE.";
              }
              leaf ngType1RtNum {
                type uint32;
                config false;
                description
                  "Number of Intra-AS I-PMSI A-D Routes.";
              }
              leaf ngType2RtNum {
                type uint32;
                config false;
                description
                  "Number of Inter-AS I-PMSI A-D Routes.";
              }
              leaf ngType3RtNum {
                type uint32;
                config false;
                description
                  "Number of S-PMSI A-D Routes.";
              }
              leaf ngType4RtNum {
                type uint32;
                config false;
                description
                  "Number of Leaf A-D Routes.";
              }
              leaf ngType5RtNum {
                type uint32;
                config false;
                description
                  "Number of Source Active A-D Routes.";
              }
              leaf ngType6RtNum {
                type uint32;
                config false;
                description
                  "Number of Shared Tree Join Routes.";
              }
              leaf ngType7RtNum {
                type uint32;
                config false;
                description
                  "Number of Source Tree Join Routes.";
              }
              leaf vrfRtNum {
                type uint32;
                config false;
                description
                  "Total number of routes of Addr-family for vpn-instance.";
              }
              leaf lsNodeRtNum {
                type uint32;
                config false;
                description
                  "Total Number of Node Routes.";
              }
              leaf lsLinkRtNum {
                type uint32;
                config false;
                description
                  "Total Number of Link Routes.";
              }
              leaf lsIpv4PrefixRtNum {
                type uint32;
                config false;
                description
                  "Total Number of IPv4 Prefix Routes.";
              }
              leaf lsIpv6PrefixRtNum {
                type uint32;
                config false;
                description
                  "Total Number of IPv6 Prefix Routes.";
              }
              leaf fromPeBestRtNum {
                type uint32;
                config false;
                description
                  "Total Number of Best Routes from All PE.";
              }
              leaf fromPeAdvBestRtNum {
                type uint32;
                config false;
                description
                  "Total Number of Best-external Routes from All PE.";
              }
              leaf evpnAdRtNum {
                type uint32;
                config false;
                description
                  "Number of A-D Routes.";
              }
              leaf evpnMacRtNum {
                type uint32;
                config false;
                description
                  "Number of Mac Routes.";
              }
              leaf evpnInclusRtNum {
                type uint32;
                config false;
                description
                  "Number of Inclusive Multicast Routes.";
              }
              leaf evpnEsRtNum {
                type uint32;
                config false;
                description
                  "Number of ES Routes.";
              }
              leaf evpnIpPrefRtNum {
                type uint32;
                config false;
                description
                  "Number of Ip Prefix Routes.";
              }
              leaf evpnArpRtNum {
                type uint32;
                config false;
                description
                  "Number of ARP Routes.";
              }
            }
            container bgpVtRtStaticsInfo {
              config false;
              description
                "Display BGP vpn-target route statics info.";
              leaf fromPeRtTotalNum {
                type uint32;
                config false;
                description
                  "Total number of routes from all PE.";
              }
              container bgpVtRouteStatics {
                config false;
                description
                  "bgpVtRouteStatics.";
                list bgpVtRouteStatic {
                  key "originAs";
                  config false;
                  description
                    "bgpVtRtStaticsInfo.";
                  leaf originAs {
                    type asNumberValidate;
                    config false;
                    description
                      "Origin-As.";
                  }
                  leaf rtTotalNum {
                    type uint32;
                    config false;
                    description
                      "rtTotalNum.";
                  }
                }
              }
            }			
            container adRoutingTables {
              when "not(../afType='ipv4vpnmcast' or ../afType='mdt' or ../afType='vpntarget' or ../afType='vpnv4flow')";
              config false;
              description
                "Information about AD routes in the EVPN address family.";
              list adRoutingTable {
                when "../../afType='evpn'";
                key "rd adPrefix routeTypeFlag";
                config false;
                description
                  "Information about AD routes in the EVPN address family.";
                leaf rd {
                  type string {
                    length "0..60";
                  }
                  config false;
                  description
                    "Route distinguisher. An RD is in the format of 32-bit IP address:16-bit user-defined number, for example, 192.168.122.15:1. The IP address ranges from 0.0.0.0 to 255.255.255.255, and the user-defined number ranges from 0 to 65536. An EVN address family takes effect only after it is configured with a RD.";
                }
                leaf adPrefix {
                  type string {
                    length "0..60";
                  }
                  config false;
                  description
                    "AD route prefix.";
                }
                leaf routeTypeFlag {
                  type pub-type:bits32;
                  config false;
                  description
                    "Route type.";
                  ext:masklen 32;
                    ext:bit "ibgp" {
                      position 0;
                    }
                    ext:bit "ebgp" {
                      position 1;
                    }
                    ext:bit "network" {
                      position 2;
                    }
                    ext:bit "import" {
                      position 3;
                    }
                    ext:bit "auto-summary" {
                      position 4;
                    }
                    ext:bit "aggregate" {
                      position 5;
                    }
                    ext:bit "cpri" {
                      position 6;
                    }
                    ext:bit "pcri" {
                      position 7;
                    }
                    ext:bit "suppressed" {
                      position 8;
                    }
                    ext:bit "NHP-EMPTY" {
                      position 9;
                    }
                    ext:bit "NO-ADV" {
                      position 10;
                    }
                    ext:bit "local_cross" {
                      position 11;
                    }
                    ext:bit "remote_cross" {
                      position 12;
                    }
                    ext:bit "VD-BGP" {
                      position 13;
                    }
                    ext:bit "PATH_LOCAL" {
                      position 14;
                    }
                    ext:bit "PATH_GATEWAY" {
                      position 15;
                    }
                    ext:bit "policy_nopass" {
                      position 16;
                    }
                    ext:bit "supprenet" {
                      position 17;
                    }
                    ext:bit "dampened" {
                      position 18;
                    }
                    ext:bit "history" {
                      position 19;
                    }
                    ext:bit "select" {
                      position 20;
                    }
                    ext:bit "best" {
                      position 21;
                    }
                    ext:bit "backup" {
                      position 22;
                    }
                    ext:bit "attr_change" {
                      position 23;
                    }
                    ext:bit "NHLFE_CREATED" {
                      position 24;
                    }
                    ext:bit "ILM_CREATED" {
                      position 25;
                    }
                    ext:bit "NEXTHOP_CHANGE" {
                      position 26;
                    }
                    ext:bit "Invaild" {
                      position 27;
                    }
                    ext:bit "SOURCE_CHANGE" {
                      position 28;
                    }
                    ext:bit "IN_SELECTEDQ" {
                      position 29;
                    }
                    ext:bit "EXITIF_ERROR" {
                      position 30;
                    }
                    ext:bit "GROUP_HEAD" {
                      position 31;
                    }
                }
                leaf nexthop {
                  type inet:ip-address-no-zone;
                  config false;
                  description
                    "Next-hop address to which packets are sent.";
                }
                leaf locPrf {
                  type uint32 {
                    range "0..4294967295";
                  }
                  config false;
                  description
                    "Local priority.";
                }
                leaf prefVal {
                  type uint32 {
                    range "0..4294967295";
                  }
                  config false;
                  description
                    "Preferred value of a protocol.";
                }
                leaf prefrence {
                  type uint8 {
                    range "0..255";
                  }
                  config false;
                  description
                    "Preference of a route.";
                }
                leaf pathAs {
                  type string {
                    length "1..300";
                  }
                  config false;
                  description
                    "List of the ASs that packets pass through.";
                }
                leaf origin {
                  type bgpcommOrigin;
                  config false;
                  description
                    "Origin of a route.";
                }
                leaf med {
                  type uint32 {
                    range "0..4294967295";
                  }
                  config false;
                  description
                    "Route MED in the attribute node.";
                }
                leaf flagString {
                  type string {
                    length "1..100";
                  }
                  config false;
                  description
                    "Route flag that contains a string of characters.";
                }
                leaf rtWorseReason {
                  type string {
                    length "1..50";
                  }
                  config false;
                  description
                    "Reason why a route is not selected.";
                }
                leaf peerString {
                  type string {
                    length "1..300";
                  }
                  config false;
                  description
                    "List of sending peers.";
                }
                leaf time {
                  type uint32 {
                    range "0..4294967295";
                  }
                  config false;
                  description
                    "Time stamp of a route.";
                }
                leaf extCommunity {
                  type string {
                    length "1..120";
                  }
                  config false;
                  description
                    "Extended community attribute.";
                }
                leaf from {
                  type inet:ip-address-no-zone;
                  config false;
                  description
                    "Source peer that sends a route.";
                }
                leaf ifName {
                  type string {
                    length "1..63";
                  }
                  config false;
                  description
                    "Name of the outbound interface of a route.";
                }
                leaf originator {
                  type inet:ipv4-address-no-zone;
                  config false;
                  description
                    "Router ID of the route initiator.";
                }
                leaf remoteRouteId {
                  type inet:ipv4-address-no-zone;
                  config false;
                  description
                    "Router ID of a peer.";
                }
                leaf relayNexthop {
                  type inet:ip-address-no-zone;
                  config false;
                  description
                    "Iterated next hop.";
                }
                leaf relaytnlName {
                  type string {
                    length "0..64";
                  }
                  config false;
                  description
                    "Name of an iteration tunnel.";
                }
                leaf inLabel {
                  type uint32 {
                    range "0..4294967295";
                  }
                  config false;
                  description
                    "In-label.";
                }
                leaf outLabel {
                  type uint32 {
                    range "0..4294967295";
                  }
                  config false;
                  description
                    "Out-label.";
                }
                leaf pmsiString {
                  type string {
                    length "0..300";
                  }
                  config false;
                  description
                    "PMSI attribute.";
                }
                leaf attrString {
                  type string {
                    length "0..300";
                  }
                  config false;
                  description
                    "Other attribute.";
                }
                leaf community {
                  type string {
                    length "0..120";
                  }
                  config false;
                  description
                    "Community attribute.";
                }
                leaf clusterList {
                  type string {
                    length "0..300";
                  }
                  config false;
                  description
                    "List of cluster IDs.";
                }
              }
            }
            container bgpAdvRoutes {
              description
                "List of Advertise Route Protocol.";
              list bgpAdvRoute {
                key "protocol";
                description
                  "Advertise Route Protocol.";
                leaf protocol {
                  type bgpcommAdvRouteProtocol;
                  description
                    "Route Protocol.";
                }
              }
            }
            container bgpSlowPeerInfos {
              config false;
              description
                "Slow peer list.";
              list bgpSlowPeerInfo {
                key "remoteAddress";
                config false;
                description
                  "Slow peer information.";
                leaf remoteAddress {
                  type inet:ip-address-no-zone;
                  config false;
                  description
                    "Slow peer address.";
                }
                leaf slowLastEndTime {
                  type yang:date-and-time;
                  config false;
                  description
                    "The last time of slow neighbors as nomal.";
                }
                leaf slowStartTime {
                  type yang:date-and-time;
                  config false;
                  description
                    "The time of neighbor is detected as slow neighbor.";
                }
                leaf slowCount {
                  type uint32;
                  config false;
                  description
                    "Slow peer count.";
                }
              }
            }
            container bgpRtFilterInfos {
              config false;
              description
                "bgpRtFilterInfos";
              list bgpRtFilterInfo {
                when "not(../../afType='vpnv4flow')";
                key "peerAddr rt";
                config false;
                description
                  "bgpRtFilterInfo";
                leaf peerAddr {
                  type inet:ip-address-no-zone;
                  config false;
                  description
                    "Address of a peer.";
                }
                leaf rtFilterNum {
                  type uint32;
                  config false;
                  description
                    "rtFilterNum";
                }
                leaf rt {
                  type string {
                    length "1..60";
                  }
                  config false;
                  description
                    "Prefix of a BGP route.";
                }
                leaf rtRefCount {
                  type uint32;
                  config false;
                  description
                    "rtRefCount";
                }
                leaf prefixMask {
                  type uint32;
                  config false;
                  description
                    "prefixMask";
                }
              }
            }
            container bgpRdRoutingTables {
              config false;
              description
                "List of information about RD routes.";
              list bgpRdRoutingTable {
                key "networkPrefix prefixMask routeTypeFlag imTableId rd from pathID";
                config false;
                description
                  "Display information about RD routes.";
                leaf networkPrefix {
                  type inet:ip-address-no-zone;
                  config false;
                  description
                    "BGP route prefix.";
                }
                leaf prefixMask {
                  type uint8;
                  config false;
                  description
                    "Prefix mask.";
                }
                leaf routeTypeFlag {
                  type pub-type:bits32 {
                    ext:masklen 32;
                      ext:bit "ibgp" {
                        position 0;
                      }
                      ext:bit "ebgp" {
                        position 1;
                      }
                      ext:bit "network" {
                        position 2;
                      }
                      ext:bit "import" {
                        position 3;
                      }
                      ext:bit "auto-summary" {
                        position 4;
                      }
                      ext:bit "aggregate" {
                        position 5;
                      }
                      ext:bit "cpri" {
                        position 6;
                      }
                      ext:bit "pcri" {
                        position 7;
                      }
                      ext:bit "suppressed" {
                        position 8;
                      }
                      ext:bit "NHP-EMPTY" {
                        position 9;
                      }
                      ext:bit "NO-ADV" {
                        position 10;
                      }
                      ext:bit "local_cross" {
                        position 11;
                      }
                      ext:bit "remote_cross" {
                        position 12;
                      }
                      ext:bit "VD-BGP" {
                        position 13;
                      }
                      ext:bit "PATH_LOCAL" {
                        position 14;
                      }
                      ext:bit "PATH_GATEWAY" {
                        position 15;
                      }
                      ext:bit "policy_nopass" {
                        position 16;
                      }
                      ext:bit "supprenet" {
                        position 17;
                      }
                      ext:bit "dampened" {
                        position 18;
                      }
                      ext:bit "history" {
                        position 19;
                      }
                      ext:bit "select" {
                        position 20;
                      }
                      ext:bit "best" {
                        position 21;
                      }
                      ext:bit "backup" {
                        position 22;
                      }
                      ext:bit "attr_change" {
                        position 23;
                      }
                      ext:bit "NHLFE_CREATED" {
                        position 24;
                      }
                      ext:bit "ILM_CREATED" {
                        position 25;
                      }
                      ext:bit "NEXTHOP_CHANGE" {
                        position 26;
                      }
                      ext:bit "Invaild" {
                        position 27;
                      }
                      ext:bit "SOURCE_CHANGE" {
                        position 28;
                      }
                      ext:bit "IN_SELECTEDQ" {
                        position 29;
                      }
                      ext:bit "EXITIF_ERROR" {
                        position 30;
                      }
                      ext:bit "GROUP_HEAD" {
                        position 31;
                      }
                  }
                  config false;
                  description
                    "Route type.";
                }
                leaf imTableId {
                  type uint32 {
                    range "0..4294967295";
                  }
                  config false;
                  description
                    "ID of the routing table to which routes are imported.";
                }
                leaf rd {
                  type string {
                    length "1..22";
                  }
                  config false;
                  description
                    "Route distinguisher.";
                }
                leaf from {
                  type inet:ip-address-no-zone;
                  config false;
                  description
                    "Source peer that sends a route.";
                }
                leaf pathID {
                  type string {
                    length "1..50";
                  }
                  config false;
                  description
                    "Path ID.";
                }
                leaf remoteNextHopTunnelAddress {
                  type inet:ip-address-no-zone;
                  config false;
                  description
                    "The remote next hop tunnel address.";
                }
                leaf remoteNextHopMacAddress {
                  type pub-type:macAddress;
                  config false;
                  description
                    "The remote next hop mac.";
                }
                leaf nexthop {
                  type inet:ip-address-no-zone;
                  config false;
                  description
                    "Next hop address to which packets are forwarded.";
                }
                leaf locPrf {
                  type uint32 {
                    range "0..4294967295";
                  }
                  config false;
                  description
                    "Local-preference.";
                }
                leaf prefVal {
                  type uint32 {
                    range "0..4294967295";
                  }
                  config false;
                  description
                    "Preferred value of a protocol.";
                }
                leaf prefrence {
                  type uint8 {
                    range "0..255";
                  }
                  config false;
                  description
                    "Priority of BGP routes.";
                }
                leaf pathAs {
                  type string {
                    length "1..300";
                  }
                  config false;
                  description
                    "List of the AS_Paths that packets pass through.";
                }
                leaf origin {
                  type bgpcommOrigin;
                  config false;
                  description
                    "Route origin.";
                }
                leaf med {
                  type uint32 {
                    range "0..4294967295";
                  }
                  config false;
                  description
                    "Route MED.";
                }
                leaf flagString {
                  type string {
                    length "1..100";
                  }
                  config false;
                  description
                    "Route flag that contains a string of characters.";
                }
                leaf rtWorseReason {
                  type string {
                    length "1..50";
                  }
                  config false;
                  description
                    "Reason why a route is not selected.";
                }
                leaf peerString {
                  type string {
                    length "1..300";
                  }
                  config false;
                  description
                    "List of route sending peers.";
                }
                leaf time {
                  type uint32 {
                    range "0..4294967295";
                  }
                  config false;
                  description
                    "Time stamp of a route.";
                }
                leaf community {
                  type string {
                    length "1..120";
                  }
                  config false;
                  description
                    "Community attribute.";
                }
                leaf extCommunity {
                  type string {
                    length "1..300";
                  }
                  config false;
                  description
                    "Extended community attribute.";
                }
                leaf ifName {
                  type pub-type:ifName;
                  config false;
                  description
                    "Name of the outbound interface of a route.";
                }
                leaf originator {
                  type inet:ip-address-no-zone;
                  config false;
                  description
                    "Router ID of the route initiator.";
                }
                leaf clusterList {
                  type string {
                    length "1..300";
                  }
                  config false;
                  description
                    "List of cluster IDs.";
                }
                leaf remoteRouteId {
                  type inet:ipv4-address-no-zone;
                  config false;
                  description
                    "Router ID of a peer.";
                }
                leaf relayNexthop {
                  type inet:ip-address-no-zone;
                  config false;
                  description
                    "Next hop to which a route is iterated.";
                }
                leaf relaytnlName {
                  type string {
                    length "1..64";
                  }
                  config false;
                  description
                    "Name of a tunnel to which a route is iterated.";
                }
                leaf isAtomicAggre {
                  type boolean;
                  default "false";
                  config false;
                  description
                    "Route carrying the atomic-aggregate attribute.";
                }
                leaf aggregatorAs {
                  type string {
                    length "1..11";
                  }
                  config false;
                  description
                    "AS number of the route summarizer.";
                }
                leaf aggregatorId {
                  type inet:ip-address-no-zone;
                  config false;
                  description
                    "ID of the route summarizer.";
                }
                leaf inLabel {
                  type uint32 {
                    range "0..4294967295";
                  }
                  config false;
                  description
                    "In-label.";
                }
                leaf outLabel {
                  type uint32 {
                    range "0..4294967295";
                  }
                  config false;
                  description
                    "Out-label.";
                }
                leaf disAttrString {
                  type string {
                    length "1..300";
                  }
                  config false;
                  description
                    "Discard the route attribute list.";
                }
                leaf vrfName {
                  type string {
                    length "1..31";
                  }
                  config false;
                  description
                    "Relay VRF.";
                }
                leaf remoteNextHopVni {
                  type uint32 {
                    range "0..4294967295";
                  }
                  config false;
                  description
                    "The remote next hop vni.";
                }
                leaf advNextHop {
                  type inet:ip-address-no-zone;
                  config false;
                  description
                    "Advertise nexthop.";
                }
                leaf prefixSid {
                  type string {
                    length "1..60";
                  }
                  config false;
                  description
                    "PrefixSid attribute infomation of Route.";
                }
                leaf aigp {
                  type uint64;
                  config false;
                  description
                    "AIGP attribute information of Route.";
                }
                leaf attrSetString {
                  type string {
                    length "1..300";
                  }
                  config false;
                  description
                    "The attribute set information of Route.";
                }
              }
            }
            container bgpNexthopInfo {
              config false;
              description
                "Information about BGP address faimly nexthop.";
              leaf relayCnt {
                type uint32;
                config false;
                description
                  "Relay nexthop count.";
              }
              leaf localCrossCnt {
                type uint32;
                config false;
                description
                  "Local cross route relay nexthop count.";
              }
              leaf remoteCrossCnt {
                type uint32;
                config false;
                description
                  "Remote cross route relay nexthop count.";
              }
              leaf importBaseCnt {
                type uint32;
                config false;
                description
                  "Import base count.";
              }
              leaf importExtendCnt {
                type uint32;
                config false;
                description
                  "Import extend count.";
              }
              leaf networkCnt {
                type uint32;
                config false;
                description
                  "Network route count.";
              }
              container peerNextHopInfos {
                config false;
                description
                  "List of display the BGP peer nexthop.";
                list peerNextHopInfo {
                  key "origNexthop";
                  config false;
                  description
                    "Information about display the  BGP peer nexthop.";
                  leaf origNexthop {
                    type inet:ip-address-no-zone;
                    config false;
                    description
                      "Original nexthop.";
                  }
                  leaf originalType {
                    type string {
                      length "1..300";
                    }
                    config false;
                    description
                      "Original nexthop type.";
                  }
                  leaf rd {
                    type string {
                      length "1..60";
                    }
                    config false;
                    description
                      "Route distinguisher.";
                  }
                  leaf userData {
                    type string {
                      length "1..60";
                    }
                    config false;
                    description
                      "User data  information.";
                  }
                  leaf tunlPlyName {
                    type string {
                      length "1..200";
                    }
                    config false;
                    description
                      "Tunnel policy name.";
                  }
                  leaf relayType {
                    type string {
                      length "1..100";
                    }
                    config false;
                    description
                      "Relay type.";
                  }
                  leaf redirectKey {
                    type string {
                      length "1..100";
                    }
                    config false;
                    description
                      "Redirect key.";
                  }
                  leaf iId {
                    type uint32;
                    config false;
                    description
                      "IID.";
                    ext:support-filter "true";
                  }
                  leaf rtRelayLastChTime {
                    type string {
                      length "1..60";
                    }
                    config false;
                    description
                      "Relay IP last change time.";
                  }
                  leaf rtRelayStatus {
                    type string {
                      length "1..60";
                    }
                    config false;
                    description
                      "Relay status.";
                  }
                  leaf rtRelayIid {
                    type uint32;
                    config false;
                    description
                      "Relay ID.";
                  }
                  leaf rtRelayCost {
                    type uint32;
                    config false;
                    description
                      "Relay cost.";
                  }
                  leaf rtRelayNum {
                    type uint32;
                    config false;
                    description
                      "Relay number.";
                  }
                  leaf rtRelayDepth {
                    type uint32;
                    config false;
                    description
                      "Relay depth.";
                  }
                  leaf rtRestrainCnt {
                    type uint32;
                    config false;
                    description
                      "Restrain count.";
                  }
                  leaf rtRestLeftTime {
                    type uint32;
                    config false;
                    description
                      "Restrain time left.";
                  }
                  leaf firstRelayRtNhp {
                    type inet:ip-address-no-zone;
                    config false;
                    description
                      "First relay nexthop.";
                  }
                  leaf firstRelayRtLabel {
                    type uint32;
                    config false;
                    description
                      "First relay label.";
                  }
                  leaf firstRelayRtOutIntf {
                    type string {
                      length "1..300";
                    }
                    config false;
                    description
                      "First relay out interface.";
                  }
                  leaf firstRelayRtSour {
                    type inet:ip-address-no-zone;
                    config false;
                    description
                      "First relay route source.";
                  }
                  leaf firstRelayRtPlyRes {
                    type string {
                      length "1..60";
                    }
                    config false;
                    description
                      "First relay policy result.";
                  }
                  leaf firstTnlName {
                    type string {
                      length "1..200";
                    }
                    config false;
                    description
                      "First relay tunnel name.";
                  }
                  leaf firstRelayTnlId {
                    type uint32;
                    config false;
                    description
                      "First relay tunnel id.";
                  }
                  leaf firstVrfName {
                    type string {
                      length "1..60";
                    }
                    config false;
                    description
                      "First relay VPN-Instance name.";
                  }
                  leaf firstRelayTnlLabel {
                    type uint32;
                    config false;
                    description
                      "First relay tunnel label.";
                  }
                  leaf secRelayRtNhp {
                    type inet:ip-address-no-zone;
                    config false;
                    description
                      "Second relay nexthop.";
                  }
                  leaf secRelayRtLabel {
                    type uint32;
                    config false;
                    description
                      "Second relay label.";
                  }
                  leaf secRelayRtOutInt {
                    type string {
                      length "1..300";
                    }
                    config false;
                    description
                      "Second relay out interface.";
                  }
                  leaf secRelayRtSour {
                    type inet:ip-address-no-zone;
                    config false;
                    description
                      "Second relay route source.";
                  }
                  leaf secRelayRtPlyRes {
                    type string {
                      length "1..60";
                    }
                    config false;
                    description
                      "Second relay policy result.";
                  }
                  leaf secTnlName {
                    type string {
                      length "1..200";
                    }
                    config false;
                    description
                      "Second relay tunnel name.";
                  }
                  leaf secRelayTnlId {
                    type uint32;
                    config false;
                    description
                      "Second relay tunnel Id.";
                  }
                  leaf secVrfName {
                    type string {
                      length "1..60";
                    }
                    config false;
                    description
                      "Second relay VPN-Instance name.";
                  }
                  leaf secRelayTnlLabel {
                    type uint32;
                    config false;
                    description
                      "Second relay tunnel label.";
                  }
                  leaf tnlRelayLastChTime {
                    type string {
                      length "1..60";
                    }
                    config false;
                    description
                      "Relay tunnel last change time.";
                  }
                  leaf tnlRelayStatus {
                    type string {
                      length "1..60";
                    }
                    config false;
                    description
                      "Relay tunnel status.";
                  }
                  leaf tnlRelayIid {
                    type uint32;
                    config false;
                    description
                      "Relay tunnel IID.";
                  }
                  leaf tnlRelayCost {
                    type uint32;
                    config false;
                    description
                      "Relay tunnel cost.";
                  }
                  leaf tnlRelayNum {
                    type uint32;
                    config false;
                    description
                      "Relay tunnel number.";
                  }
                  leaf tnlRelayDepth {
                    type uint32;
                    config false;
                    description
                      "Relay tunnel depth.";
                  }
                  leaf tnlRestrainCnt {
                    type uint32;
                    config false;
                    description
                      "Relay tunnel restrain count.";
                  }
                  leaf tnlRestLeftTime {
                    type uint32;
                    config false;
                    description
                      "Relay tunnel restrain time left.";
                  }
                  leaf firDelayTnlName {
                    type string {
                      length "1..200";
                    }
                    config false;
                    description
                      "First relay tunnel name.";
                  }
                  leaf secDelayTnlName {
                    type string {
                      length "1..200";
                    }
                    config false;
                    description
                      "Second relay tunnel name.";
                  }
                  leaf cir {
                    type uint32;
                    config false;
                    description
                      "Relay tunnel CIR(Committed Information Rate).";
                  }
                  leaf pir {
                    type uint32;
                    config false;
                    description
                      "Relay tunnel PIR(Peak Information Rate).";
                  }
                  leaf tnlVrfName {
                    type string {
                      length "1..60";
                    }
                    config false;
                    description
                      "Relay tunnel VPN-Instance name.";
                  }
                  leaf tnlIdStr {
                    type string {
                      length "1..300";
                    }
                    config false;
                    description
                      "Relay tunnel id.";
                  }
                  leaf rtRedLastChTime {
                    type string {
                      length "1..60";
                    }
                    config false;
                    description
                      "Redirect information last change time.";
                  }
                  leaf rtRedStatus {
                    type string {
                      length "1..100";
                    }
                    config false;
                    description
                      "Route redirect status.";
                  }
                  leaf rtRedIiD {
                    type uint32;
                    config false;
                    description
                      "Route redirect IID.";
                  }
                  leaf rtRedOutIntf {
                    type string {
                      length "1..300";
                    }
                    config false;
                    description
                      "Route redirect out interface.";
                  }
                  leaf rtRedVlan {
                    type string {
                      length "1..100";
                    }
                    config false;
                    description
                      "Route redirect vlan.";
                  }
                  leaf ipDelayFlapCnt {
                    type uint32;
                    config false;
                    description
                      "IP relay flap count.";
                  }
                  leaf tnlDelayFlapCnt {
                    type uint32;
                    config false;
                    description
                      "Tunnel relay flap count.";
                  }
                }
              }
            }
            container bgpNetworkInfos {
              config false;
              description
                "List of network routes information.";
              list bgpNetworkInfo {
                key "network maskLength";
                config false;
                description
                  "Displays the routes imported into the BGP routing table using the network command.";
                leaf network {
                  type inet:ip-address-no-zone;
                  config false;
                  description
                    "Locally imported network address.";
                }
                leaf maskLength {
                  type uint8 {
                    range "0..128";
                  }
                  config false;
                  description
                    "Mask length of an IP address.";
                }
                leaf mask {
                  type inet:ipv4-address-no-zone;
                  config false;
                  description
                    "Mask of the network address.";
                }
                leaf routePolicyName {
                  type string {
                    length "1..200";
                  }
                  config false;
                  description
                    "Route policy.";
                }
              }
            }
            container bgpRtTableLabels {
              config false;
              description
                "List of displays the labeled routes in the BGP routing table.";
              list bgpRtTableLabel {
                key "network maskLength nextHop";
                config false;
                description
                  "Information about displays the labeled routes in the BGP routing table.";
                leaf network {
                  type inet:ip-address-no-zone;
                  config false;
                  description
                    "Network address in the BGP routing table.";
                }
                leaf maskLength {
                  type uint8 {
                    range "0..128";
                  }
                  config false;
                  description
                    "Network address mask length in the BGP routing table.";
                }
                leaf nextHop {
                  type inet:ip-address-no-zone;
                  config false;
                  description
                    "IP address of the reachable next hop.";
                }
                leaf inLabel {
                  type uint32 {
                    range "0..4294967295";
                  }
                  config false;
                  description
                    "In-label.";
                }
                leaf outLabel {
                  type uint32 {
                    range "0..4294967295";
                  }
                  config false;
                  description
                    "Out-label.";
                }
              }
            }
            container rpdRoutingTables {
              when "../afType='rpd'";
              config false;
              description
                "RPD routing tables.";
              uses bgp:bgp_bgpcomm_rpdRoutingTables_type;
            }
          }
        }
        container bgpPeerBfdSessionInfos {
          config false;
          description
            "List of BFD sessions.";
          list bgpPeerBfdSessionInfo {
            key "remoteAddress";
            config false;
            description
              "BFD session.";
            leaf remoteAddress {
              type inet:ip-address-no-zone;
              config false;
              description
                "Peer address of the BFD session.";
            }
            leaf localAddress {
              type inet:ip-address-no-zone;
              config false;
              description
                "Local address of the BFD session.";
            }
            leaf ifName {
              type pub-type:ifName;
              config false;
              description
                "Name of an interface of the BFD session.";
            }
            leaf txInterval {
              type uint32 {
                range "0..4294967295";
              }
              default "0";
              config false;
              description
                "Interval at which BFD packets are sent, in milliseconds.";
            }
            leaf rxInterval {
              type uint32 {
                range "0..4294967295";
              }
              default "0";
              config false;
              description
                "Interval at which BFD packets are received, in milliseconds.";
            }
            leaf multiplier {
              type uint32 {
                range "0..50";
              }
              config false;
              description
                "Detection multiplier. ";
            }
            leaf sessionState {
              type bgpBfdState;
              config false;
              description
                "State of the BFD session.";
            }
            leaf bfdGlobalEnable {
              type boolean;
              config false;
              description
                "Global BFD state.";
            }
          }
        }
      }
    }
    container vrfAllRoutingTables {
      when "not(../bgpSite/bgpEnable='false')";
      config false;
      description
        "List of displayed VPN route information.";
      list vrfAllRoutingTable {
        key "showVrfName afType networkPrefix prefixMask routeTypeFlag imTableId rd from pathID";
        config false;
        description
          "Information about A VPN route.";
        leaf showVrfName {
          type string {
            length "1..300";
          }
          config false;
          description
            "BGP instance name.";
        }
        leaf afType {
          type bgpcommPrefixType;
          config false;
          description
            "BGP address family type.";
        }
        leaf networkPrefix {
          type inet:ip-address-no-zone;
          config false;
          description
            "BGP route prefix.";
        }
        leaf prefixMask {
          type uint8;
          config false;
          description
            "Prefix mask.";
        }
        leaf routeTypeFlag {
          type pub-type:bits32;
          config false;
          description
            "Route type.";
          ext:masklen 32;
            ext:bit "ibgp" {
              position 0;
            }
            ext:bit "ebgp" {
              position 1;
            }
            ext:bit "network" {
              position 2;
            }
            ext:bit "import" {
              position 3;
            }
            ext:bit "auto-summary" {
              position 4;
            }
            ext:bit "aggregate" {
              position 5;
            }
            ext:bit "cpri" {
              position 6;
            }
            ext:bit "pcri" {
              position 7;
            }
            ext:bit "suppressed" {
              position 8;
            }
            ext:bit "NHP-EMPTY" {
              position 9;
            }
            ext:bit "NO-ADV" {
              position 10;
            }
            ext:bit "local_cross" {
              position 11;
            }
            ext:bit "remote_cross" {
              position 12;
            }
            ext:bit "VD-BGP" {
              position 13;
            }
            ext:bit "PATH_LOCAL" {
              position 14;
            }
            ext:bit "PATH_GATEWAY" {
              position 15;
            }
            ext:bit "policy_nopass" {
              position 16;
            }
            ext:bit "supprenet" {
              position 17;
            }
            ext:bit "dampened" {
              position 18;
            }
            ext:bit "history" {
              position 19;
            }
            ext:bit "select" {
              position 20;
            }
            ext:bit "best" {
              position 21;
            }
            ext:bit "backup" {
              position 22;
            }
            ext:bit "attr_change" {
              position 23;
            }
            ext:bit "NHLFE_CREATED" {
              position 24;
            }
            ext:bit "ILM_CREATED" {
              position 25;
            }
            ext:bit "NEXTHOP_CHANGE" {
              position 26;
            }
            ext:bit "Invaild" {
              position 27;
            }
            ext:bit "SOURCE_CHANGE" {
              position 28;
            }
            ext:bit "IN_SELECTEDQ" {
              position 29;
            }
            ext:bit "EXITIF_ERROR" {
              position 30;
            }
            ext:bit "GROUP_HEAD" {
              position 31;
            }
        }
        leaf imTableId {
          type uint32 {
            range "0..4294967295";
          }
          config false;
          description
            "ID of the routing table to which routes are imported.";
        }
        leaf nexthop {
          type inet:ip-address-no-zone;
          config false;
          description
            "Next hop address to which packets are forwarded.";
        }
        leaf locPrf {
          type uint32 {
            range "0..4294967295";
          }
          config false;
          description
            "Local-preference.";
        }
        leaf prefVal {
          type uint32 {
            range "0..4294967295";
          }
          config false;
          description
            "Preferred value of a protocol.";
        }
        leaf prefrence {
          type uint8 {
            range "0..255";
          }
          config false;
          description
            "Priority of BGP routes.";
        }
        leaf pathAs {
          type string {
            length "1..300";
          }
          config false;
          description
            "List of the AS_Paths that packets pass through.";
        }
        leaf origin {
          type bgpcommOrigin;
          config false;
          description
            "Route origin.";
        }
        leaf med {
          type uint32 {
            range "0..4294967295";
          }
          config false;
          description
            "Route MED.";
        }
        leaf flagString {
          type string {
            length "1..100";
          }
          config false;
          description
            "Route flag that contains a string of characters.";
        }
        leaf rd {
          type string {
            length "1..22";
          }
          config false;
          description
            "Route distinguisher.";
        }
        leaf rtWorseReason {
          type string {
            length "1..50";
          }
          config false;
          description
            "Reason why a route is not selected.";
        }
        leaf peerString {
          type string {
            length "1..300";
          }
          config false;
          description
            "List of route sending peers.";
        }
        leaf time {
          type uint32 {
            range "0..4294967295";
          }
          config false;
          description
            "Time stamp of a route.";
        }
        leaf community {
          type string {
            length "1..120";
          }
          config false;
          description
            "Community attribute.";
        }
        leaf extCommunity {
          type string {
            length "1..300";
          }
          config false;
          description
            "Extended community attribute.";
        }
        leaf from {
          type inet:ip-address-no-zone;
          config false;
          description
            "Source peer that sends a route.";
        }
        leaf ifName {
          type pub-type:ifName;
          config false;
          description
            "Name of the outbound interface of a route.";
        }
        leaf originator {
          type inet:ip-address-no-zone;
          config false;
          description
            "Router ID of the route initiator.";
        }
        leaf clusterList {
          type string {
            length "1..300";
          }
          config false;
          description
            "List of cluster IDs.";
        }
        leaf remoteRouteId {
          type inet:ipv4-address-no-zone;
          config false;
          description
            "Router ID of a peer.";
        }
        leaf relayNexthop {
          type inet:ip-address-no-zone;
          config false;
          description
            "Next hop to which a route is iterated.";
        }
        leaf relaytnlName {
          type string {
            length "1..64";
          }
          config false;
          description
            "Name of a tunnel to which a route is iterated.";
        }
        leaf isAtomicAggre {
          type boolean;
          default "false";
          config false;
          description
            "Route carrying the atomic-aggregate attribute.";
        }
        leaf aggregatorAs {
          type string {
            length "1..11";
          }
          config false;
          description
            "AS number of the route summarizer.";
        }
        leaf aggregatorId {
          type inet:ip-address-no-zone;
          config false;
          description
            "ID of the route summarizer.";
        }
        leaf inLabel {
          type uint32 {
            range "0..4294967295";
          }
          config false;
          description
            "In-label.";
        }
        leaf outLabel {
          type uint32 {
            range "0..4294967295";
          }
          config false;
          description
            "Out-label.";
        }
        leaf pathID {
          type string {
            length "1..50";
          }
          config false;
          description
            "Path ID.";
        }
        leaf disAttrString {
          type string {
            length "1..300";
          }
          config false;
          description
            "Discard the route attribute list.";
        }
        leaf vrfName {
          type string {
            length "1..31";
          }
          config false;
          description
            "Iterated Vrf .";
        }
        leaf remoteNextHopTunnelAddress {
          type inet:ip-address-no-zone;
          config false;
          description
            "The remote next hop tunnel address.";
        }
        leaf remoteNextHopVni {
          type uint32 {
            range "0..4294967295";
          }
          config false;
          description
            "The remote next hop vni.";
        }
        leaf remoteNextHopMacAddress {
          type pub-type:macAddress;
          config false;
          description
            "The Remote next hop mac.";
        }
        leaf prefixSid {
          type string {
            length "1..60";
          }
          config false;
          description
            "PrefixSid attribute information of VRF Route.";
        }
        leaf aigp {
          type uint64;
          config false;
          description
            "AIGP attribute information of VRF Route.";
        }
      }
    }
    container bgpLsp {
      description
        "BGP LSP configuration and query items.";
      container bgpLspBfd {
        description
          "The information of dynamic BFD for BGP LSP.";
        container bgpLspBfdParameter {
          description
            "Parameters of BFD for BGP LSP.";
          leaf bgpBfdEnable {
            type boolean;
            must "(/mpls:mpls/mpls:mplsCommon/mpls:mplsCommonCfg/mpls:mplsEnable='true' and /bfd:bfd/bfd:bfdSchGlobal/bfd:bfdEnable='true') or (not(/mpls:mpls/mpls:mplsCommon/mpls:mplsCommonCfg/mpls:mplsEnable='true' and /bfd:bfd/bfd:bfdSchGlobal/bfd:bfdEnable='true') and ../bgpBfdEnable='false')";
            default "false";
            description
              "Enable dynamic BFD for BGP LSP.";
          }
          leaf bgpBfdMinTx {
            when "/mpls:mpls/mpls:mplsCommon/mpls:mplsCommonCfg/mpls:mplsEnable='true'";
            type uint32 {
              range "3..1000";
            }
            units ms;
            description
              "Interval at which BFD packets are sent. The value ranges from 3 to 1000, in milliseconds.";
            ext:allowDelete "true";
          }
          leaf bgpBfdMinRx {
            when "/mpls:mpls/mpls:mplsCommon/mpls:mplsCommonCfg/mpls:mplsEnable='true'";
            type uint32 {
              range "3..1000";
            }
            units ms;
            description
              "Interval at which BFD packets are received. The value ranges from 3 to 1000, in milliseconds.";
            ext:allowDelete "true";
          }
          leaf bgpBfdDetectMultiplier {
            type uint32 {
              range "3..50";
            }
            must "(/mpls:mpls/mpls:mplsCommon/mpls:mplsCommonCfg/mpls:mplsEnable='true') or (not(/mpls:mpls/mpls:mplsCommon/mpls:mplsCommonCfg/mpls:mplsEnable='true') and ../bgpBfdDetectMultiplier='3')";
            default "3";
            description
              "BFD detection multiplier. The value ranges from 3 to 50. The default value is 3.";
          }
          leaf bgpBfdTrigger {
            type bgpBfdTriggerType;
            must "(/mpls:mpls/mpls:mplsCommon/mpls:mplsCommonCfg/mpls:mplsEnable='true' and /bfd:bfd/bfd:bfdSchGlobal/bfd:bfdEnable='true') or (not(/mpls:mpls/mpls:mplsCommon/mpls:mplsCommonCfg/mpls:mplsEnable='true' and /bfd:bfd/bfd:bfdSchGlobal/bfd:bfdEnable='true') and ../bgpBfdTrigger='none')";
            default "none";
            description
              "Configure a policy for creating BGP LSP BFD sessions.";
          }
          leaf bgpBfdTriggerIpPrefix {
            when "not(../bgpBfdTrigger!='ip-prefix')";
            type leafref {
              path "/rtp:rtp/rtp:prefixFilters/rtp:prefixFilter/rtp:name";
            }
            description
              "To use an IP prefix list to dynamically create BFD sessions, specify a name of the IP prefix list.";
            ext:allowDelete "true";
          }
        }
        container bgpLspBfdSessions {
          config false;
          description
            "Display all the sessions of dynamic BFD for BGP LSP.";
          list bgpLspBfdSession {
            key "fecAddress outIfName nextHop";
            config false;
            description
              "Display a session of dynamic BFD for BGP LSP.";
            leaf fecAddress {
              type inet:ipv4-address-no-zone;
              config false;
              description
                "Display the FEC address of the session of dynamic BFD for BGP LSP.";
            }
            leaf outIfName {
              type pub-type:ifName;
              config false;
              description
                "Display the outbound interface of a BGP LSP.";
            }
            leaf nextHop {
              type inet:ipv4-address-no-zone;
              config false;
              description
                "Display the next hop of a BGP LSP.";
            }
            leaf lspIndex {
              type uint32;
              config false;
              description
                "Display the LSP index of a BGP LSP.";
            }
            leaf bfdDiscriminator {
              type uint32;
              config false;
              description
                "Display the BFD discriminator of the BFD session of dynamic BFD for BGP LSP.";
            }
            leaf sessionState {
              type bgpLspBfdSessionState;
              config false;
              description
                "Display the BFD session state of dynamic BFD for BGP LSP.";
            }
            leaf minTxInt {
              type uint32;
              config false;
              description
                "Display the minimum interval at which BFD packets of the session of dynamic BFD for BGP LSP are sent. The value is expressed in milliseconds.";
            }
            leaf minRxInt {
              type uint32;
              config false;
              description
                "Display the minimum interval at which BFD packets of the session of dynamic BFD for BGP LSP are received. The value is expressed in milliseconds.";
            }
            leaf detectMulti {
              type uint32;
              config false;
              description
                "Display the BFD detection multiplier of the BFD session of dynamic BFD for BGP LSP.";
            }
            leaf sessionAge {
              type uint32;
              config false;
              description
                "Display the BFD session age of dynamic BFD for BGP LSP.";
            }
          }
        }
      }
      container bgpLspInfos {
        config false;
        description
          "List of BGP LSPs.";
        list bgpLspInfo {
          key "vrfName afType lspAddr prefixLength lspIndex lspType indirectID frrType";
          config false;
          description
            "BGP LSP.";
          leaf vrfName {
            type string {
              length "1..32";
            }
            config false;
            description
              "Name of a BGP instance.";
          }
          leaf vrfRD {
            type string {
              length "3..21";
            }
            config false;
            description
              "A VPN address family takes effect only after it is configured with an RD. The format of an RD is as follows:
1. 16-bit AS number:32-bit user-defined number, for example, 101:3. An AS number ranges from 0 to 65535, and a user-defined number ranges from 0 to 4294967295. The AS number and user-defined number cannot be both 0s. This means that the RD value cannot be 0:0.
2. 32-bit IP address:16-bit user-defined number, for example: 192.168.122.15:1. The IP address ranges from 0.0.0.0 to 255.255.255.255, and the user-defined number ranges from 0 to 65535.
3. 32-bit AS number:16-bit user-defined number, for example, 10.11:3. An AS number ranges from 0.0 to 65535.65535 or from 0 to 4294967295, and a user-defined number ranges from 0 to 65535. The AS number and user-defined number cannot be both 0s. This means that the RD value cannot be 0.0:0.";
          }
          leaf afType {
            type bgpcommPrefixType;
            config false;
            description
              "Specifies the address family type of a BGP instance. ";
          }
          leaf lspAddr {
            type inet:ip-address-no-zone;
            config false;
            description
              "Destination address of an LSP.";
          }
          leaf prefixLength {
            type uint32 {
              range "0..128";
            }
            config false;
            description
              "Prefix length of the destination address of an LSP.";
          }
          leaf lspIndex {
            type uint32;
            config false;
            description
              "LSP index.";
          }
          leaf lspType {
            type bgpLspType;
            config false;
            description
              "LSP type.";
          }
          leaf inIfaceName {
            type pub-type:ifName;
            config false;
            description
              "Inbound interface of an LSP.";
          }
          leaf outIfaceName {
            type pub-type:ifName;
            config false;
            description
              "Outbound interface of an LSP.";
          }
          leaf indirectID {
            type string {
              length "1..50";
            }
            config false;
            description
              "IndirectID.";
          }
          leaf nextHop {
            type inet:ip-address-no-zone;
            config false;
            description
              "Next hop of an LSP.";
          }
          leaf frrType {
            type bgpLspFrrType;
            config false;
            description
              "FRR role.";
          }
          leaf lspMtu {
            type uint32 {
              range "0..65535";
            }
            config false;
            description
              "LSP MTU.";
          }
          leaf lspTimeStamp {
            type uint32 {
              range "0..4294967295";
            }
            config false;
            description
              "LSP duration.";
          }
          leaf inLabel {
            type uint32 {
              range "0..4294967295";
            }
            config false;
            description
              "In-label of an LSP.";
          }
          leaf outLabel {
            type uint32 {
              range "0..4294967295";
            }
            config false;
            description
              "Out-label of an LSP.";
          }
          leaf outGoingTunnelId {
            type string {
              length "1..50";
            }
            config false;
            description
              "Index of an outbound LSP.";
          }
          leaf labelOperationType {
            type bgpLabelOperationType;
            config false;
            description
              "Label operation type.";
          }
          leaf expMode {
            type bgpcommExpModeType;
            config false;
            description
              "QoS Priority Mode of an LSP.";
          }
          leaf tunnelID {
            type string {
              length "1..50";
            }
            config false;
            description
              "ID of an Outbound LSP";
          }
          container bgpLspTnlInfos {
            config false;
            description
              "Tunnel Infornation.";
            list bgpLspTnlInfo {
              key "tunnelKey";
              config false;
              description
                "Tunnel Infornation List.";
              leaf tunnelKey {
                type string {
                  length "1..50";
                }
                config false;
                description
                  "tunnelKey.";
              }
            }
          }
        }
      }
    }
    container bgpEvrfs {
      when "not(../bgpSite/bgpEnable='false')";
      config false;
      description
        "EVPN private instance list.";
      list bgpEvrf {
        key "vrfName";
        config false;
        max-elements  "4096";
        description
          "EVPN private instance.";
        leaf vrfName {
          type string {
            length "1..31";
          }
          config false;
          description
            "Name of an EVPN instance.";
        }
        container interfaceEsiInfos {
          config false;
          description
            "ESI list.";
          list interfaceEsiInfo {
            key "effectEsi";
            config false;
            description
              "ESI.";
            leaf effectEsi {
              type string {
                length "1..60";
              }
              config false;
              description
                "Effective ESI.";
            }
            leaf dyminalEsi {
              type string {
                length "1..60";
              }
              config false;
              description
                "Dynamic ESI.";
            }
            leaf staticEsi {
              type string {
                length "1..60";
              }
              config false;
              description
                "Static ESI.";
            }
            container ifLists {
              config false;
              description
                "Interface information list.";
              list ifList {
                key "ifName";
                config false;
                description
                  "Interface information.";
                leaf ifName {
                  type pub-type:ifName;
                  config false;
                  description
                    "Interface Name.";
                }
              }
            }
          }
        }
        container dfTimerInfos {
          config false;
          description
            "DF timer list.";
          list dfTimerInfo {
            key "esi";
            config false;
            description
              "DF timer.";
            leaf esi {
              type string {
                length "1..60";
              }
              config false;
              description
                "Effective ESI.";
            }
            leaf ifName {
              type pub-type:ifName;
              config false;
              description
                "Interface Name.";
            }
            leaf timerType {
              type dfTimerType;
              config false;
              description
                "DF election timer type.";
            }
            leaf timerMode {
              type dfTimerMode;
              config false;
              description
                "DF election timer mode.";
            }
            leaf timerLeftTime {
              type uint32;
              config false;
              description
                "Time to elapse before a DF election timer expires, expressed in seconds.";
            }
          }
        }
        container dfResults {
          config false;
          description
            "DF election result list.";
          list dfResult {
            key "esi ifName";
            config false;
            description
              "DF election result.";
            leaf esi {
              type string {
                length "1..60";
              }
              config false;
              description
                "Effective ESI.";
            }
            leaf ifName {
              type pub-type:ifName;
              config false;
              description
                "Interface Name.";
            }
            leaf dfResult {
              type dfResultType;
              config false;
              description
                "DF election result.";
            }
          }
        }
        container ipPrefixRoutingTables {
          config false;
          description
            "List of Prefix routes in the EVPN address family.";
          list ipPrefixRoutingTable {
            key "rd ipPrefix routeTypeFlag";
            config false;
            description
              "Prefix route.";
            leaf rd {
              type string {
                length "1..60";
              }
              config false;
              description
                "Route distinguisher. An RD is in the format of 32-bit IP address:16-bit user-defined number, for example, 192.168.122.15:1. The IP address ranges from 0.0.0.0 to 255.255.255.255, and the user-defined number ranges from 0 to 65536. An EVN address family takes effect only after it is configured with a RD.";
            }
            leaf ipPrefix {
              type string {
                length "1..60";
              }
              config false;
              description
                "Prefix route prefix.";
            }
            leaf routeTypeFlag {
              type pub-type:bits32;
              config false;
              description
                "Route type.";
              ext:masklen 32;
                ext:bit "ibgp" {
                  position 0;
                }
                ext:bit "ebgp" {
                  position 1;
                }
                ext:bit "network" {
                  position 2;
                }
                ext:bit "import" {
                  position 3;
                }
                ext:bit "auto-summary" {
                  position 4;
                }
                ext:bit "aggregate" {
                  position 5;
                }
                ext:bit "cpri" {
                  position 6;
                }
                ext:bit "pcri" {
                  position 7;
                }
                ext:bit "suppressed" {
                  position 8;
                }
                ext:bit "NHP-EMPTY" {
                  position 9;
                }
                ext:bit "NO-ADV" {
                  position 10;
                }
                ext:bit "local_cross" {
                  position 11;
                }
                ext:bit "remote_cross" {
                  position 12;
                }
                ext:bit "VD-BGP" {
                  position 13;
                }
                ext:bit "PATH_LOCAL" {
                  position 14;
                }
                ext:bit "PATH_GATEWAY" {
                  position 15;
                }
                ext:bit "policy_nopass" {
                  position 16;
                }
                ext:bit "supprenet" {
                  position 17;
                }
                ext:bit "dampened" {
                  position 18;
                }
                ext:bit "history" {
                  position 19;
                }
                ext:bit "select" {
                  position 20;
                }
                ext:bit "best" {
                  position 21;
                }
                ext:bit "backup" {
                  position 22;
                }
                ext:bit "attr_change" {
                  position 23;
                }
                ext:bit "NHLFE_CREATED" {
                  position 24;
                }
                ext:bit "ILM_CREATED" {
                  position 25;
                }
                ext:bit "NEXTHOP_CHANGE" {
                  position 26;
                }
                ext:bit "Invaild" {
                  position 27;
                }
                ext:bit "SOURCE_CHANGE" {
                  position 28;
                }
                ext:bit "IN_SELECTEDQ" {
                  position 29;
                }
                ext:bit "EXITIF_ERROR" {
                  position 30;
                }
                ext:bit "GROUP_HEAD" {
                  position 31;
                }
            }
            leaf nexthop {
              type inet:ip-address-no-zone;
              config false;
              description
                "Next-hop address to which packets are sent.";
            }
            leaf locPrf {
              type uint32 {
                range "0..4294967295";
              }
              config false;
              description
                "Local priority.";
            }
            leaf prefVal {
              type uint32 {
                range "0..4294967295";
              }
              config false;
              description
                "Preferred value of a protocol.";
            }
            leaf prefrence {
              type uint8 {
                range "0..255";
              }
              config false;
              description
                "Preference of a route.";
            }
            leaf pathAs {
              type string {
                length "1..300";
              }
              config false;
              description
                "List of the ASs that packets pass through.";
            }
            leaf origin {
              type bgpcommOrigin;
              config false;
              description
                "Origin of a route.";
            }
            leaf med {
              type uint32 {
                range "0..4294967295";
              }
              config false;
              description
                "Route MED.";
            }
            leaf flagString {
              type string {
                length "1..100";
              }
              config false;
              description
                "Route flag in the format of a character string.";
            }
            leaf peerString {
              type string {
                length "1..300";
              }
              config false;
              description
                "List of sending peers.";
            }
            leaf time {
              type uint32 {
                range "0..4294967295";
              }
              config false;
              description
                "Time stamp of a route.";
            }
            leaf extCommunity {
              type string {
                length "1..300";
              }
              config false;
              description
                "Extended community attribute.";
            }
            leaf rtWorseReason {
              type string {
                length "1..50";
              }
              config false;
              description
                "Reason why a route is not selected.";
            }
            leaf from {
              type inet:ip-address-no-zone;
              config false;
              description
                "Source peer that sends a route.";
            }
            leaf ifName {
              type string {
                length "1..63";
              }
              config false;
              description
                "Name of the outbound interface of a route.";
            }
            leaf originator {
              type inet:ipv4-address-no-zone;
              config false;
              description
                "Router ID of the route initiator.";
            }
            leaf remoteRouteId {
              type inet:ipv4-address-no-zone;
              config false;
              description
                "Router ID of a peer.";
            }
            leaf relayNexthop {
              type inet:ip-address-no-zone;
              config false;
              description
                "Iterated next hop.";
            }
            leaf relaytnlName {
              type string {
                length "1..64";
              }
              config false;
              description
                "Name of an iteration tunnel.";
            }
            leaf inLabel {
              type uint32 {
                range "0..4294967295";
              }
              config false;
              description
                "In-label.";
            }
            leaf outLabel {
              type uint32 {
                range "0..4294967295";
              }
              config false;
              description
                "Out-label.";
            }
            leaf pmsiString {
              type string {
                length "1..300";
              }
              config false;
              description
                "PMSI attribute.";
            }
            leaf mplsLabel1 {
              type uint32 {
                range "0..4294967295";
              }
              config false;
              description
                "Label1,it means L2 VNI for MAC Route and L3 VNI for Prefix Route.";
            }
            leaf mplsLabel2 {
              type uint32 {
                range "0..4294967295";
              }
              config false;
              description
                "Label2,it means L3 VNI for MAC Route.";
            }
            leaf attrString {
              type string {
                length "1..300";
              }
              config false;
              description
                "Other attribute.";
            }
            leaf community {
              type string {
                length "1..120";
              }
              config false;
              description
                "Community attribute.";
            }
            leaf clusterList {
              type string {
                length "1..300";
              }
              config false;
              description
                "List of cluster IDs.";
            }
          }
        }
        container macRoutingTables {
          config false;
          description
            "List of MAC routes in the EVPN address family.";
          list macRoutingTable {
            key "rd macPrefix routeTypeFlag";
            config false;
            description
              "MAC route.";
            leaf rd {
              type string {
                length "1..60";
              }
              config false;
              description
                "Route distinguisher. An RD is in the format of 32-bit IP address:16-bit user-defined number, for example, 192.168.122.15:1. The IP address ranges from 0.0.0.0 to 255.255.255.255, and the user-defined number ranges from 0 to 65536.An EVN address family takes effect only after it is configured with a RD.";
            }
            leaf macPrefix {
              type string {
                length "1..60";
              }
              config false;
              description
                "MAC route prefix.";
            }
            leaf routeTypeFlag {
              type pub-type:bits32;
              config false;
              description
                "Route type.";
              ext:masklen 32;
                ext:bit "ibgp" {
                  position 0;
                }
                ext:bit "ebgp" {
                  position 1;
                }
                ext:bit "network" {
                  position 2;
                }
                ext:bit "import" {
                  position 3;
                }
                ext:bit "auto-summary" {
                  position 4;
                }
                ext:bit "aggregate" {
                  position 5;
                }
                ext:bit "cpri" {
                  position 6;
                }
                ext:bit "pcri" {
                  position 7;
                }
                ext:bit "suppressed" {
                  position 8;
                }
                ext:bit "NHP-EMPTY" {
                  position 9;
                }
                ext:bit "NO-ADV" {
                  position 10;
                }
                ext:bit "local_cross" {
                  position 11;
                }
                ext:bit "remote_cross" {
                  position 12;
                }
                ext:bit "VD-BGP" {
                  position 13;
                }
                ext:bit "PATH_LOCAL" {
                  position 14;
                }
                ext:bit "PATH_GATEWAY" {
                  position 15;
                }
                ext:bit "policy_nopass" {
                  position 16;
                }
                ext:bit "supprenet" {
                  position 17;
                }
                ext:bit "dampened" {
                  position 18;
                }
                ext:bit "history" {
                  position 19;
                }
                ext:bit "select" {
                  position 20;
                }
                ext:bit "best" {
                  position 21;
                }
                ext:bit "backup" {
                  position 22;
                }
                ext:bit "attr_change" {
                  position 23;
                }
                ext:bit "NHLFE_CREATED" {
                  position 24;
                }
                ext:bit "ILM_CREATED" {
                  position 25;
                }
                ext:bit "NEXTHOP_CHANGE" {
                  position 26;
                }
                ext:bit "Invaild" {
                  position 27;
                }
                ext:bit "SOURCE_CHANGE" {
                  position 28;
                }
                ext:bit "IN_SELECTEDQ" {
                  position 29;
                }
                ext:bit "EXITIF_ERROR" {
                  position 30;
                }
                ext:bit "GROUP_HEAD" {
                  position 31;
                }
            }
            leaf nexthop {
              type inet:ip-address-no-zone;
              config false;
              description
                "Next-hop address to which packets are sent.";
            }
            leaf locPrf {
              type uint32 {
                range "0..4294967295";
              }
              config false;
              description
                "Local priority.";
            }
            leaf sourceAFI {
              type bgpcommPrefixType;
              config false;
              description
                "Source address Family.";
            }
            leaf sourceRD {
              type string {
                length "3..21";
              }
              config false;
              description
                "Source RD.";
            }
            leaf prefVal {
              type uint32 {
                range "0..4294967295";
              }
              config false;
              description
                "Preferred value of a protocol.";
            }
            leaf prefrence {
              type uint8 {
                range "0..255";
              }
              config false;
              description
                "Preference of a route.";
            }
            leaf pathAs {
              type string {
                length "1..300";
              }
              config false;
              description
                "List of the ASs that packets pass through.";
            }
            leaf origin {
              type bgpcommOrigin;
              config false;
              description
                "Origin of a route.";
            }
            leaf med {
              type uint32 {
                range "0..4294967295";
              }
              config false;
              description
                "Route MED.";
            }
            leaf flagString {
              type string {
                length "1..100";
              }
              config false;
              description
                "Route flag in the format of a character string.";
            }
            leaf peerString {
              type string {
                length "1..300";
              }
              config false;
              description
                "List of sending peers.";
            }
            leaf time {
              type uint32 {
                range "0..4294967295";
              }
              config false;
              description
                "Time stamp of a route.";
            }
            leaf extCommunity {
              type string {
                length "1..300";
              }
              config false;
              description
                "Extended community attribute.";
            }
            leaf rtWorseReason {
              type string {
                length "1..50";
              }
              config false;
              description
                "Reason why a route is not selected.";
            }
            leaf from {
              type inet:ip-address-no-zone;
              config false;
              description
                "Source peer that sends a route.";
            }
            leaf ifName {
              type string {
                length "1..63";
              }
              config false;
              description
                "Name of the outbound interface of a route.";
            }
            leaf originator {
              type inet:ipv4-address-no-zone;
              config false;
              description
                "Router ID of the route initiator.";
            }
            leaf remoteRouteId {
              type inet:ipv4-address-no-zone;
              config false;
              description
                "Router ID of a peer.";
            }
            leaf relayNexthop {
              type inet:ip-address-no-zone;
              config false;
              description
                "Iterated next hop.";
            }
            leaf relaytnlName {
              type string {
                length "1..64";
              }
              config false;
              description
                "Name of an iteration tunnel.";
            }
            leaf inLabel {
              type uint32 {
                range "0..4294967295";
              }
              config false;
              description
                "In-label.";
            }
            leaf outLabel {
              type uint32 {
                range "0..4294967295";
              }
              config false;
              description
                "Out-label.";
            }
            leaf pmsiString {
              type string {
                length "1..300";
              }
              config false;
              description
                "PMSI attribute.";
            }
            leaf mplsLabel1 {
              type uint32 {
                range "0..4294967295";
              }
              config false;
              description
                "Label1,it means L2 VNI for MAC Route and L3 VNI for Prefix Route.";
            }
            leaf mplsLabel2 {
              type uint32 {
                range "0..4294967295";
              }
              config false;
              description
                "Label2,it means L3 VNI for MAC Route.";
            }
            leaf attrString {
              type string {
                length "1..300";
              }
              config false;
              description
                "Other attribute.";
            }
            leaf community {
              type string {
                length "1..120";
              }
              config false;
              description
                "Community attribute.";
            }
            leaf clusterList {
              type string {
                length "1..300";
              }
              config false;
              description
                "List of cluster IDs.";
            }
            leaf frrOutIfName {
              type string {
                length "1..64";
              }
              config false;
              description
                "Local-Remote Frr Direct Out-interface.";
            }
            leaf frrNexthop {
              type inet:ipv4-address-no-zone;
              config false;
              description
                "Local-Remote Frr Nexthop.";
            }
            leaf frrTnlOutIf {
              type string {
                length "1..64";
              }
              config false;
              description
                "Local-Remote Frr Tunnel Out-Interface.";
            }
            leaf effectNexthop {
              type inet:ip-address-no-zone;
              config false;
              description
                "Effective nexthop.";
            }
            leaf redirectOutIf {
              type string {
                length "1..64";
              }
              config false;
              description
                "Redirect Out-Interface.";
            }
          }
        }
        container esRoutingTables {
          config false;
          description
            "List of ES routes in the EVN address family.";
          list esRoutingTable {
            key "rd esPrefix routeTypeFlag";
            config false;
            description
              "ES route in the EVN address family.";
            leaf rd {
              type string {
                length "1..60";
              }
              config false;
              description
                "Route distinguisher. An RD is in the format of 32-bit IP address:16-bit user-defined number, for example, 192.168.122.15:1. The IP address ranges from 0.0.0.0 to 255.255.255.255, and the user-defined number ranges from 0 to 65536. An EVN address family takes effect only after it is configured with a RD.";
            }
            leaf esPrefix {
              type string {
                length "1..60";
              }
              config false;
              description
                "ES route prefix.";
            }
            leaf routeTypeFlag {
              type pub-type:bits32;
              config false;
              description
                "Route type.";
              ext:masklen 32;
                ext:bit "ibgp" {
                  position 0;
                }
                ext:bit "ebgp" {
                  position 1;
                }
                ext:bit "network" {
                  position 2;
                }
                ext:bit "import" {
                  position 3;
                }
                ext:bit "auto-summary" {
                  position 4;
                }
                ext:bit "aggregate" {
                  position 5;
                }
                ext:bit "cpri" {
                  position 6;
                }
                ext:bit "pcri" {
                  position 7;
                }
                ext:bit "suppressed" {
                  position 8;
                }
                ext:bit "NHP-EMPTY" {
                  position 9;
                }
                ext:bit "NO-ADV" {
                  position 10;
                }
                ext:bit "local_cross" {
                  position 11;
                }
                ext:bit "remote_cross" {
                  position 12;
                }
                ext:bit "VD-BGP" {
                  position 13;
                }
                ext:bit "PATH_LOCAL" {
                  position 14;
                }
                ext:bit "PATH_GATEWAY" {
                  position 15;
                }
                ext:bit "policy_nopass" {
                  position 16;
                }
                ext:bit "supprenet" {
                  position 17;
                }
                ext:bit "dampened" {
                  position 18;
                }
                ext:bit "history" {
                  position 19;
                }
                ext:bit "select" {
                  position 20;
                }
                ext:bit "best" {
                  position 21;
                }
                ext:bit "backup" {
                  position 22;
                }
                ext:bit "attr_change" {
                  position 23;
                }
                ext:bit "NHLFE_CREATED" {
                  position 24;
                }
                ext:bit "ILM_CREATED" {
                  position 25;
                }
                ext:bit "NEXTHOP_CHANGE" {
                  position 26;
                }
                ext:bit "Invaild" {
                  position 27;
                }
                ext:bit "SOURCE_CHANGE" {
                  position 28;
                }
                ext:bit "IN_SELECTEDQ" {
                  position 29;
                }
                ext:bit "EXITIF_ERROR" {
                  position 30;
                }
                ext:bit "GROUP_HEAD" {
                  position 31;
                }
            }
            leaf nexthop {
              type inet:ip-address-no-zone;
              config false;
              description
                "Next-hop address to which packets are sent.";
            }
            leaf locPrf {
              type uint32 {
                range "0..4294967295";
              }
              config false;
              description
                "Local priority.";
            }
            leaf prefVal {
              type uint32 {
                range "0..4294967295";
              }
              config false;
              description
                "Preferred value of a protocol.";
            }
            leaf prefrence {
              type uint8 {
                range "0..255";
              }
              config false;
              description
                "Rreference of a route.";
            }
            leaf pathAs {
              type string {
                length "1..300";
              }
              config false;
              description
                "List of the ASs that packets pass through.";
            }
            leaf origin {
              type bgpcommOrigin;
              config false;
              description
                "Origin of a route.";
            }
            leaf med {
              type uint32 {
                range "0..4294967295";
              }
              config false;
              description
                "Route MED.";
            }
            leaf flagString {
              type string {
                length "1..100";
              }
              config false;
              description
                "Route flag that contains a string of characters.";
            }
            leaf rtWorseReason {
              type string {
                length "1..50";
              }
              config false;
              description
                "Reason why a route is not selected.";
            }
            leaf peerString {
              type string {
                length "1..300";
              }
              config false;
              description
                "List of sending peers.";
            }
            leaf time {
              type uint32 {
                range "0..4294967295";
              }
              config false;
              description
                "Time stamp of a route.";
            }
            leaf extCommunity {
              type string {
                length "1..300";
              }
              config false;
              description
                "Extended community attribute.";
            }
            leaf from {
              type inet:ip-address-no-zone;
              config false;
              description
                "Source peer that sends a route.";
            }
            leaf ifName {
              type string {
                length "1..63";
              }
              config false;
              description
                "Name of the outbound interface of a route.";
            }
            leaf originator {
              type inet:ipv4-address-no-zone;
              config false;
              description
                "Router ID of the route initiator.";
            }
            leaf remoteRouteId {
              type inet:ipv4-address-no-zone;
              config false;
              description
                "Router ID of a peer.";
            }
            leaf relayNexthop {
              type inet:ip-address-no-zone;
              config false;
              description
                "Iterated next hop.";
            }
            leaf relaytnlName {
              type string {
                length "1..64";
              }
              config false;
              description
                "Name of an iteration tunnel.";
            }
            leaf inLabel {
              type uint32 {
                range "0..4294967295";
              }
              config false;
              description
                "In-label.";
            }
            leaf outLabel {
              type uint32 {
                range "0..4294967295";
              }
              config false;
              description
                "Out-label.";
            }
            leaf pmsiString {
              type string {
                length "1..300";
              }
              config false;
              description
                "PMSI attribute.";
            }
            leaf attrString {
              type string {
                length "1..300";
              }
              config false;
              description
                "Other attribute.";
            }
            leaf community {
              type string {
                length "1..120";
              }
              config false;
              description
                "Community attribute.";
            }
            leaf clusterList {
              type string {
                length "1..300";
              }
              config false;
              description
                "List of cluster IDs.";
            }
          }
        }
        container multiRoutingTables {
          config false;
          description
            "List of inclusive routes information in the EVPN address family.";
          list multiRoutingTable {
            key "rd inclusivePrefix routeTypeFlag";
            config false;
            description
              "Inclusive route in the EVPN address family.";
            leaf rd {
              type string {
                length "1..60";
              }
              config false;
              description
                "Route distinguisher. An EVN address family takes effect only after it is configured with a RD. The format of an RD is as follows:32-bit IP address:16-bit user-defined number, for example: 192.168.122.15:1.The IP address ranges from 0.0.0.0 to 255.255.255.255, and the user-defined number ranges from 0 to 65536.";
            }
            leaf inclusivePrefix {
              type inet:ipv4-address-no-zone;
              config false;
              description
                "Inclusive route prefix.";
            }
            leaf routeTypeFlag {
              type pub-type:bits32;
              config false;
              description
                "Route type.";
              ext:masklen 32;
                ext:bit "ibgp" {
                  position 0;
                }
                ext:bit "ebgp" {
                  position 1;
                }
                ext:bit "network" {
                  position 2;
                }
                ext:bit "import" {
                  position 3;
                }
                ext:bit "auto-summary" {
                  position 4;
                }
                ext:bit "aggregate" {
                  position 5;
                }
                ext:bit "cpri" {
                  position 6;
                }
                ext:bit "pcri" {
                  position 7;
                }
                ext:bit "suppressed" {
                  position 8;
                }
                ext:bit "NHP-EMPTY" {
                  position 9;
                }
                ext:bit "NO-ADV" {
                  position 10;
                }
                ext:bit "local_cross" {
                  position 11;
                }
                ext:bit "remote_cross" {
                  position 12;
                }
                ext:bit "VD-BGP" {
                  position 13;
                }
                ext:bit "PATH_LOCAL" {
                  position 14;
                }
                ext:bit "PATH_GATEWAY" {
                  position 15;
                }
                ext:bit "policy_nopass" {
                  position 16;
                }
                ext:bit "supprenet" {
                  position 17;
                }
                ext:bit "dampened" {
                  position 18;
                }
                ext:bit "history" {
                  position 19;
                }
                ext:bit "select" {
                  position 20;
                }
                ext:bit "best" {
                  position 21;
                }
                ext:bit "backup" {
                  position 22;
                }
                ext:bit "attr_change" {
                  position 23;
                }
                ext:bit "NHLFE_CREATED" {
                  position 24;
                }
                ext:bit "ILM_CREATED" {
                  position 25;
                }
                ext:bit "NEXTHOP_CHANGE" {
                  position 26;
                }
                ext:bit "Invaild" {
                  position 27;
                }
                ext:bit "SOURCE_CHANGE" {
                  position 28;
                }
                ext:bit "IN_SELECTEDQ" {
                  position 29;
                }
                ext:bit "EXITIF_ERROR" {
                  position 30;
                }
                ext:bit "GROUP_HEAD" {
                  position 31;
                }
            }
            leaf nexthop {
              type inet:ip-address-no-zone;
              config false;
              description
                "Next-hop address to which packets are sent.";
            }
            leaf locPrf {
              type uint32 {
                range "0..4294967295";
              }
              config false;
              description
                "Local priority.";
            }
            leaf prefVal {
              type uint32 {
                range "0..4294967295";
              }
              config false;
              description
                "Preferred value of a protocol.";
            }
            leaf prefrence {
              type uint8 {
                range "0..255";
              }
              config false;
              description
                "Preference of a route.";
            }
            leaf pathAs {
              type string {
                length "1..300";
              }
              config false;
              description
                "List of the ASs that packets pass through.";
            }
            leaf origin {
              type bgpcommOrigin;
              config false;
              description
                "Origin of a route.";
            }
            leaf med {
              type uint32 {
                range "0..4294967295";
              }
              config false;
              description
                "Route MED in the attribute node.";
            }
            leaf flagString {
              type string {
                length "1..100";
              }
              config false;
              description
                "Route flag in the format of a character string.";
            }
            leaf rtWorseReason {
              type string {
                length "1..50";
              }
              config false;
              description
                "Reason why a route is not selected.";
            }
            leaf peerString {
              type string {
                length "1..300";
              }
              config false;
              description
                "List of sending peers.";
            }
            leaf time {
              type uint32 {
                range "0..4294967295";
              }
              config false;
              description
                "Time stamp of a route.";
            }
            leaf extCommunity {
              type string {
                length "1..300";
              }
              config false;
              description
                "Extended community attribute.";
            }
            leaf from {
              type inet:ip-address-no-zone;
              config false;
              description
                "Source peer that sends a route.";
            }
            leaf ifName {
              type string {
                length "1..63";
              }
              config false;
              description
                "Name of the outbound interface of a route.";
            }
            leaf originator {
              type inet:ipv4-address-no-zone;
              config false;
              description
                "Router ID of the route initiator.";
            }
            leaf remoteRouteId {
              type inet:ipv4-address-no-zone;
              config false;
              description
                "Router ID of a peer.";
            }
            leaf relayNexthop {
              type inet:ip-address-no-zone;
              config false;
              description
                "Iterated next hop.";
            }
            leaf relaytnlName {
              type string {
                length "1..64";
              }
              config false;
              description
                "Name of an iteration tunnel.";
            }
            leaf inLabel {
              type uint32 {
                range "0..4294967295";
              }
              config false;
              description
                "In-label.";
            }
            leaf outLabel {
              type uint32 {
                range "0..4294967295";
              }
              config false;
              description
                "Out-label.";
            }
            leaf pmsiString {
              type string {
                length "1..300";
              }
              config false;
              description
                "PMSI attribute.";
            }
            leaf attrString {
              type string {
                length "1..300";
              }
              config false;
              description
                "Other attribute.";
            }
            leaf community {
              type string {
                length "1..120";
              }
              config false;
              description
                "Community attribute.";
            }
            leaf clusterList {
              type string {
                length "1..300";
              }
              config false;
              description
                "List of cluster IDs.";
            }
          }
        }
        container adRoutingTables {
          config false;
          description
            "Information about AD routes in the EVPN address family.";
          list adRoutingTable {
            key "rd adPrefix routeTypeFlag";
            config false;
            description
              "Information about AD routes in the EVPN address family.";
            leaf rd {
              type string {
                length "1..60";
              }
              config false;
              description
                "Route distinguisher. An RD is in the format of 32-bit IP address:16-bit user-defined number, for example, 192.168.122.15:1. The IP address ranges from 0.0.0.0 to 255.255.255.255, and the user-defined number ranges from 0 to 65536. An EVN address family takes effect only after it is configured with a RD.";
            }
            leaf adPrefix {
              type string {
                length "1..60";
              }
              config false;
              description
                "AD route prefix.";
            }
            leaf routeTypeFlag {
              type pub-type:bits32;
              config false;
              description
                "Route type.";
              ext:masklen 32;
                ext:bit "ibgp" {
                  position 0;
                }
                ext:bit "ebgp" {
                  position 1;
                }
                ext:bit "network" {
                  position 2;
                }
                ext:bit "import" {
                  position 3;
                }
                ext:bit "auto-summary" {
                  position 4;
                }
                ext:bit "aggregate" {
                  position 5;
                }
                ext:bit "cpri" {
                  position 6;
                }
                ext:bit "pcri" {
                  position 7;
                }
                ext:bit "suppressed" {
                  position 8;
                }
                ext:bit "NHP-EMPTY" {
                  position 9;
                }
                ext:bit "NO-ADV" {
                  position 10;
                }
                ext:bit "local_cross" {
                  position 11;
                }
                ext:bit "remote_cross" {
                  position 12;
                }
                ext:bit "VD-BGP" {
                  position 13;
                }
                ext:bit "PATH_LOCAL" {
                  position 14;
                }
                ext:bit "PATH_GATEWAY" {
                  position 15;
                }
                ext:bit "policy_nopass" {
                  position 16;
                }
                ext:bit "supprenet" {
                  position 17;
                }
                ext:bit "dampened" {
                  position 18;
                }
                ext:bit "history" {
                  position 19;
                }
                ext:bit "select" {
                  position 20;
                }
                ext:bit "best" {
                  position 21;
                }
                ext:bit "backup" {
                  position 22;
                }
                ext:bit "attr_change" {
                  position 23;
                }
                ext:bit "NHLFE_CREATED" {
                  position 24;
                }
                ext:bit "ILM_CREATED" {
                  position 25;
                }
                ext:bit "NEXTHOP_CHANGE" {
                  position 26;
                }
                ext:bit "Invaild" {
                  position 27;
                }
                ext:bit "SOURCE_CHANGE" {
                  position 28;
                }
                ext:bit "IN_SELECTEDQ" {
                  position 29;
                }
                ext:bit "EXITIF_ERROR" {
                  position 30;
                }
                ext:bit "GROUP_HEAD" {
                  position 31;
                }
            }
            leaf nexthop {
              type inet:ip-address-no-zone;
              config false;
              description
                "Next-hop address to which packets are sent.";
            }
            leaf locPrf {
              type uint32 {
                range "0..4294967295";
              }
              config false;
              description
                "Local priority.";
            }
            leaf prefVal {
              type uint32 {
                range "0..4294967295";
              }
              config false;
              description
                "Preferred value of a protocol.";
            }
            leaf prefrence {
              type uint8 {
                range "0..255";
              }
              config false;
              description
                "Preference of a route.";
            }
            leaf pathAs {
              type string {
                length "1..300";
              }
              config false;
              description
                "List of the ASs that packets pass through.";
            }
            leaf origin {
              type bgpcommOrigin;
              config false;
              description
                "Origin of a route.";
            }
            leaf med {
              type uint32 {
                range "0..4294967295";
              }
              config false;
              description
                "Route MED in the attribute node.";
            }
            leaf flagString {
              type string {
                length "1..100";
              }
              config false;
              description
                "Route flag that contains a string of characters.";
            }
            leaf rtWorseReason {
              type string {
                length "1..50";
              }
              config false;
              description
                "Reason why a route is not selected.";
            }
            leaf peerString {
              type string {
                length "1..300";
              }
              config false;
              description
                "List of sending peers.";
            }
            leaf time {
              type uint32 {
                range "0..4294967295";
              }
              config false;
              description
                "Time stamp of a route.";
            }
            leaf extCommunity {
              type string {
                length "1..300";
              }
              config false;
              description
                "Extended community attribute.";
            }
            leaf from {
              type inet:ip-address-no-zone;
              config false;
              description
                "Source peer that sends a route.";
            }
            leaf ifName {
              type string {
                length "1..63";
              }
              config false;
              description
                "Name of the outbound interface of a route.";
            }
            leaf originator {
              type inet:ipv4-address-no-zone;
              config false;
              description
                "Router ID of the route initiator.";
            }
            leaf remoteRouteId {
              type inet:ipv4-address-no-zone;
              config false;
              description
                "Router ID of a peer.";
            }
            leaf relayNexthop {
              type inet:ip-address-no-zone;
              config false;
              description
                "Iterated next hop.";
            }
            leaf relaytnlName {
              type string {
                length "1..64";
              }
              config false;
              description
                "Name of an iteration tunnel.";
            }
            leaf inLabel {
              type uint32 {
                range "0..4294967295";
              }
              config false;
              description
                "In-label.";
            }
            leaf outLabel {
              type uint32 {
                range "0..4294967295";
              }
              config false;
              description
                "Out-label.";
            }
            leaf pmsiString {
              type string {
                length "1..300";
              }
              config false;
              description
                "PMSI attribute.";
            }
            leaf attrString {
              type string {
                length "1..300";
              }
              config false;
              description
                "Other attribute.";
            }
            leaf community {
              type string {
                length "1..120";
              }
              config false;
              description
                "Community attribute.";
            }
            leaf clusterList {
              type string {
                length "1..300";
              }
              config false;
              description
                "List of cluster IDs.";
            }
          }
        }
      }
    }
    container bgpInsts {
      when "not(../bgpSite/bgpEnable='false')";
      config false;
      description
        "Index Name List of BGP instance.";
      list bgpInst {
        key "bgpName";
        config false;
        max-elements  "32";
        description
          "Index Name of a BGP instance.";
        leaf bgpName {
          type string {
            length "1..31";
          }
          config false;
          description
            "Name of a BGP instance.";
        }
      }
    }
    container bgpVrfAlarms {
      when "not(../bgpSite/bgpEnable='false')";
      description
        "BGP VRF Alarms.";
      list bgpVrfAlarm {
        key "afType vrfName";
        description
          "BGP VRF Alarm.";
        leaf afType {
          type bgpcommPrefixType;
          description
            "Specifies the address family type of a BGP instance. ";
        }
        leaf vrfName {
          type string {
            length "1..31";
          }
          description
            "Name of an VPN instance.";
        }
        leaf almRtThr {
          type uint32 {
            range "1..4294967295";
          }
          mandatory true;
          description
            "Specify the alarm route threshold.";
        }
        leaf rtThrRecyPer {
          type uint32 {
            range "1..95";
          }
          default "80";
          description
            "Specify the alarm route recovery percentage.";
          ext:allowDelete "true";
        }
      }
    }
    container bgpGrState {
      config false;
      description
        "Display the GR status of a BGP speaker.";
      leaf isGrCfg {
        type boolean;
        config false;
        description
          "The GR capability of a BGP speaker.";
      }
      leaf restartTimerCfg {
        type uint32;
        config false;
        description
          "Period during which a BGP speaker waits for the peer relationship reestablishment.";
      }
      leaf waitForEorTimer {
        type uint32;
        config false;
        description
          "Period during which a BGP speaker waits for the End-Of-RIB flag.";
      }
      container peerGrStates {
        config false;
        description
          "Display the GR status list of a BGP peer.";
        list peerGrState {
          key "vrfName addrFmType peerAddress peerCapability";
          config false;
          description
            "Display the GR status of a BGP peer.";
          leaf vrfName {
            type string {
              length "1..300";
            }
            config false;
            description
              "Name of a BGP instance.";
          }
          leaf addrFmType {
            type string {
              length "1..300";
            }
            config false;
            description
              "BGP address-family type.";
          }
          leaf peerAddress {
            type inet:ip-address-no-zone;
            config false;
            description
              "Address of a peer.";
          }
          leaf peerCapability {
            type string {
              length "1..300";
            }
            config false;
            description
              "GR capability of a neighbor.";
          }
          leaf isGrCapability {
            type boolean;
            config false;
            description
              "Whether GR capability is negotiated.";
          }
          leaf bgpPeerState {
            type bgpcommPEERSTATE;
            config false;
            description
              "Status of the peer.";
          }
          leaf isGrState {
            type boolean;
            config false;
            description
              "GR status of a neighbor.";
          }
          leaf restartLeftTimer {
            type uint32;
            config false;
            description
              "Restart left timer.";
          }
          leaf isEorSent {
            type boolean;
            config false;
            description
              "Whether error is sent.";
          }
          leaf staleRouteNum {
            type uint32;
            config false;
            description
              "Stale route number.";
          }
        }
      }
    }
    container bgpDefaultPara {
      config false;
      description
        "BGP default parameter value.";
      leaf bgpVersion {
        type uint8;
        config false;
        description
          "BGP protocol version.";
      }
      leaf prefExternalDef {
        type uint8;
        config false;
        description
          "The protocol priority of EBGP routes.";
      }
      leaf prefInternalDef {
        type uint8;
        config false;
        description
          "The protocol priority of IBGP routes.";
      }
      leaf prefLocalDef {
        type uint8;
        config false;
        description
          "The protocol priority of local BGP routes.";
      }
      leaf bgpConnRetryTime {
        type uint16;
        config false;
        description
          "Connect retry interval, in seconds.";
      }
      leaf bgpHoldTime {
        type uint32;
        config false;
        description
          "Hold time, in seconds.";
      }
      leaf bgpKeepaliveTime {
        type uint32;
        config false;
        description
          "Keepalive time, in seconds.";
      }
      leaf ebgpRtUpdtIntv {
        type uint16;
        config false;
        description
          "The update time of EBGP routes.";
      }
      leaf ibgpRtUpdtIntv {
        type uint16;
        config false;
        description
          "The update time of IBGP routes.";
      }
      leaf defLocalPref {
        type uint32;
        config false;
        description
          "The local preference of BGP routes.";
      }
      leaf defMed {
        type uint32;
        config false;
        description
          "The Multi-Exit-Discriminator (MED) of BGP routes.";
      }
      leaf defIpv4uni {
        type boolean;
        config false;
        description
          "BGP-IPv4 unicast address family view.";
      }
      leaf ebgpIfSensi {
        type boolean;
        config false;
        description
          "Interface fast sensing.";
      }
      leaf refBwClient {
        type boolean;
        config false;
        description
          "Route reflection between clients.";
      }
      leaf checkFirstAs {
        type boolean;
        config false;
        description
          "Check the first AS.";
      }
      leaf synchronization {
        type boolean;
        config false;
        description
          "Synchronization.";
      }
      leaf suppAddrFmStr {
        type string {
          length "1..600";
        }
        config false;
        description
          "Supported address family.";
      }
    }
  }
}
